;;;===========================================================================
;;; RepDblock.lsp  --  интеграция / подмена динамического блока
;;;                    из буфера обмена в текущий DWG
;;;
;;; Основная команда:
;;;   RDB (RepDblock, ПОДМЕНАБЛОКА, ПДБ, INTEGRATE)  -- полная замена/интеграция
;;;
;;; Служебные и диагностические команды:
;;;   RDBCHECK (INTEGRATECHECK, ПДБЧЕК)    -- скан без изменений (Этап 2)
;;;   RDBDUMP (INTDUMP, ПДБДАМП)           -- диагностика экземпляра (Этап 0.5)
;;;   RDBDUMPDEF (INTDUMPDEF, ПДБДАМПОПР)  -- диагностика определения (Этап 0.5)
;;;   RDBPASTETEST (INTPASTETEST)          -- диагностика вставки из буфера (Этап 0.6)
;;;   RDBTESTBED (INTTESTBED, ПДБСТЕНД)    -- построение тестового стенда (Этап 0)
;;;   RDBCLEANUP (INTCLEANUP, ПДБОЧИСТКА)  -- очистка определений прошлой интеграции
;;;   RDBCOUNT (INTCOUNT, ПДБСЧЁТ)         -- снимок таблицы блоков: вставок на определение
;;;   RDBBRIEF (INTBRIEF, ПДБКРАТКО)       -- короткая выжимка: чем кончилась очистка
;;;   RDBREPORT (INTREPORT, ПДБОТЧЁТ)      -- полный отчёт последнего прогона без шума PURGE
;;;   RDBERR (INTERR, ПДБОШИБКА)           -- короткий отчёт об ошибке (для отправки в чат)
;;;   RDBDIAG (INTDIAG, ПДБДИАГ)           -- диагностика чтения чертежа
;;;   RDBDBXTEST (INTDBXTEST, ПДБТЕСТDBX)  -- проверка глубокого клонирования (ObjectDBX)
;;;   RDBRENAMETEST (INTRENAMETEST)        -- проба переименования и динамики
;;;
;;; ГЛАВНЫЙ ПРИНЦИП: источник истины -- содержимое буфера обмена.
;;; Имена вида "ABC1.01(15)Стойка" в ТЗ -- только примеры. Программа
;;; берёт семейство и номер итерации из того определения, которое реально
;;; пришло из буфера, а набор вариантов (суффиксов) -- из того, что реально
;;; найдено в текущем файле.
;;;
;;; Архитектура (подробности в docs/README.md):
;;;   Раздел 1  утилиты
;;;   Раздел 2  парсер имени блока                       [чистое ядро]
;;;   Раздел 3  модель чертежа и сканирование            [чистое ядро]
;;;   Раздел 4  планирование интеграции                  [чистое ядро]
;;;   Раздел 5  валидация                                [чистое ядро]
;;;   Раздел 6  контракт адаптера БД
;;;   Раздел 7  шаги интеграции и оркестрация            [чистое ядро + адаптер]
;;;   Раздел 8  исполняющий слой AutoCAD (COM / entget)
;;;
;;; Разделы 2-5 и 7 не обращаются к AutoCAD напрямую: они работают с моделью
;;; чертежа в виде списков и с функциями-адаптерами KG_DB*/KG_EX*. Благодаря
;;; этому вся логика исполняется тестами (tests/run_tests.py) без AutoCAD.
;;;===========================================================================

(if (not (boundp 'KG-TESTING)) (setq KG-TESTING nil))

;; Удалять ли старые определения после перевода ссылок на новые.
;; По умолчанию nil: по п. 8.4 и 14.4 ТЗ неиспользуемые определения
;; автоматически не удаляются.
(if (not (boundp 'KG-DELETE-OLD-DEFS)) (setq KG-DELETE-OLD-DEFS nil))

;; INTCLEANUP по умолчанию работает молча: снимает только то, что нигде
;; не вставлено, поэтому спрашивать не о чем. Если нужно подтверждение --
;; (setq KG-CLEANUP-ASK t) до запуска команды.
(if (not (boundp 'KG-CLEANUP-ASK)) (setq KG-CLEANUP-ASK nil))

;; Очистка определений прошлой интеграции в конце INTEGRATE. По
;; умолчанию включена: снимается только то, что нигде не вставлено, а
;; PURGE вставленное не трогает по построению. Отключается
;; (setq KG-AUTOCLEAN nil) -- тогда остаётся ручной INTCLEANUP.
(if (not (boundp 'KG-AUTOCLEAN)) (setq KG-AUTOCLEAN t))

;; Удалять ли свои определения самим, через vla-Delete. По умолчанию НЕТ:
;; на чертеже со 100 заменёнными экземплярами удаление динамического
;; определения «Комплект КП50 v1.5 стойка КП45302-1», у которого 281
;; анонимное представление, дало 0xC0000005 -- причём не в момент
;; удаления, а на следующем проходе по таблице блоков. PURGE снимает те
;; же определения своим механизмом и проверен на реальном чертеже.
;; Включается для диагностики: (setq KG-CLEANUP-DELETE t).
(if (not (boundp 'KG-CLEANUP-DELETE)) (setq KG-CLEANUP-DELETE nil))

;; Стирать ли сиротские анонимные представления (*U) самим, через ENTD.
;; По умолчанию ДА. Повод -- реальный прогон: PURGE снял 110 определений,
;; но 180 сиротских *U остались на месте, и вместе с ними остались шесть
;; старых вложенных определений «...~до»: PURGE не заглядывает внутрь
;; анонимного представления, поэтому для него «kps 920~до» выглядит
;; использованным, а сами *U он не снимает вообще. Стирание *U с нулём
;; вставок открывает эти определения, и их уносит следующий PURGE.
;; Отключается (setq KG-CLEANUP-ERASE-U nil) -- тогда остаётся только
;; PURGE, как было в сборке 36.
(if (not (boundp 'KG-CLEANUP-ERASE-U)) (setq KG-CLEANUP-ERASE-U t))

;; 72.7. Буфер последнего отчёта. Команда RDB печатает отчёт по семьям,
;; но в журнале AutoCAD он теряется среди сотен строк PURGE. KG-Say и
;; KG-SayKV складывают те же строки в буфер; RDBREPORT выводит их
;; отдельно, уже без служебного шума. Буфер сбрасывается в начале RDB.
(setq KG-REPORT-CAPTURE nil)
(setq KG-REPORT-BUF nil)
(setq KG-REPORT-LAST nil)
(setq KG-REPORT-ALL nil)
;; 72.7. Диагностика динамических свойств: handle, имя свойства и значение,
;; которые не удалось записать. Сбрасывается перед каждым семейством.
(setq KG-DYN-FAIL nil)

;; 71.8 / 72.4. Перед PURGE перепривязывать у вставок паспорта динамики:
;; rep-data (жёсткая ссылка 340 на запись определения) держит
;; определения-кандидаты («~имя» и остатки) так, что PURGE их не удаляет --
;; сеть динамики держит записи без ссылок по имени. Ссылки переводятся на
;; записи действующих одноимённых определений, паспорта НЕ снимаются:
;; снятие в сборках до 72.4 рвало имена живых вложенных динамических блоков
;; (в Свойствах оставалось «*U462»). Вставки и геометрия *U не меняются.
;; Отключается (setq KG-CLEANUP-STRIP nil) -- тогда останется только PURGE.
(if (not (boundp 'KG-CLEANUP-STRIP)) (setq KG-CLEANUP-STRIP t))

;; Причина последнего отказа KG_EXEraseAnonDef: "minsert" (внутри
;; многострочная вставка), "noent" (не найден ename записи), "entdel"
;; (ENTD не отдал определение), "left" (определение читается и после
;; ENTD), "ok" (стёрто). По ней отчёт очистки разбирает отказы: по
;; одному «не удалось: 43» не видно, что именно мешает.
(if (not (boundp 'KG-ERASE-WHY)) (setq KG-ERASE-WHY ""))

;; Текст отказа ENTD у последней попытки стирания (пусто -- отказ без
;; ошибки). По «ENTD отказал: 38» не видно, ЧЕМ платформа объясняет отказ:
;; счётчик один и тот же у «ENTD вернул nil» и у «ENTD выбросил ошибку».
(if (not (boundp 'KG-ERASE-ERR)) (setq KG-ERASE-ERR ""))

;; Куда смотрело чтение состояний вложенных блоков у последнего экземпляра:
;; "*U" -- анонимное представление, "ОПРЕДЕЛЕНИЕ" -- родительское
;; определение (представления у вставки нет), "НЕТ" -- вложенных вставок не
;; найдено. Нужен отчёту: по одному нулю нельзя отличить «состояний не
;; было» от «искали не там».
(if (not (boundp 'KG-LAST-NESTED-SRC)) (setq KG-LAST-NESTED-SRC "НЕТ"))

;; Печатать ли промежуточные шаги. Включается командой INTEGRATE:
;; когда что-то падает внутри AutoCAD, по последнему напечатанному шагу
;; видно, где именно.
(if (not (boundp 'KG-VERBOSE)) (setq KG-VERBOSE nil))

;; Какое имя мастер-версии сейчас переименовано и в какое (пара
;; старое . временное) либо nil. Нужна обработчику ошибок: если команда
;; упадёт между освобождением имени и завершением, определение надо
;; вернуть обратно, иначе в списке блоков останется "~ИМЯ".

;; Номер сборки. Печатается при загрузке и в начале INTEGRATE: по нему
;; видно, тот ли файл загружен в AutoCAD.
(if (not (boundp 'KG-MASTER-FREED)) (setq KG-MASTER-FREED nil))

;; Переименования, выполненные командой C:INTEGRATE ДО вставки из буфера.
;; KG-Integrate_Model в режиме вставки берёт их отсюда: освобождать имена
;; после вставки уже поздно, а переименовывать пришедшие определения
;; нельзя -- содержимое снова стало бы старым.
(if (not (boundp 'KG-PRERENAMES)) (setq KG-PRERENAMES nil))

;; Снимок таблицы блоков, сделанный C:INTEGRATE ДО освобождения имён.
(if (not (boundp 'KG-PREDEFS)) (setq KG-PREDEFS nil))

;; Определения, которые реально пришли из буфера.
(if (not (boundp 'KG-ARRIVED)) (setq KG-ARRIVED nil))

;; Сколько имён освобождено ДО вставки и какие из них не удалось
;; переименовать. Без этих чисел отчёт не отличает «имена не
;; освобождались» от «освобождались, но буфер ничего не принёс».
(if (not (boundp 'KG-FREED-N)) (setq KG-FREED-N 0))
(if (not (boundp 'KG-PRE-CANDIDATES)) (setq KG-PRE-CANDIDATES 0))
(if (not (boundp 'KG-PRENAME-FAILED)) (setq KG-PRENAME-FAILED nil))

;; Причины, по которым не удалось получить интерфейс ObjectDBX.
(if (not (boundp 'KG-DBX-ERR)) (setq KG-DBX-ERR nil))

;; Что стало с определением мастер-версии после вставки из буфера.
;; Проверяется по именам и по handle: PASTECLIP молча игнорирует
;; конфликтующее определение, и тогда мастер остался бы СТАРЫМ.
(if (not (boundp 'KG-MASTER-STATE)) (setq KG-MASTER-STATE nil))

;; Сколько экземпляров КАЖДОГО варианта уже было на новой итерации ДО
;; замены: (вариант . число). Без этой поправки отчёт сравнивает «стало»
;; со числом только СТАРЫХ экземпляров и показывает ложное расхождение.
(if (not (boundp 'KG-ALREADYNEW)) (setq KG-ALREADYNEW nil))

;; Кто держит ссылки на переименованные определения. Переименование через
;; vla-put-Name правит группу 2 у вставок сам, но на реальном чертеже после
;; прогона осталось 31 определение «имя~до» с нулём вставок, и PURGE их не
;; снял. Значит, часть ссылок AutoCAD не обновил -- в первую очередь внутри
;; других определений и внутри анонимных представлений.
;;
;; 71.7. Прежний KG-REWHOLD кэшировал ответ на КАЖДОЕ ИМЯ-КЛЮЧ, а у пар
;; перепривязки имена разные: прогон 71.6 на одном семействе дал 612 пар и
;; 56.8 с в «держатели ссылки» (42.4 с из них -- обходы содержимого
;; определений), ещё 28.1 с -- тот же обход в очистке, где он не находил
;; ни одной ссылки. Теперь карта «имя -> кто вставляет» строится один раз
;; на запуск шага KG-Step_RewireDefs (KG-RefMapBuild), каждая правка ссылок
;; правит её точечно (KG-RefMapRewire), а в конце шага карта сбрасывается
;; (KG-RefMapDrop): между шагами чертёж меняют другие шаги.
;; KG-REFREV-ON -- признак «карта построена и верна»: по нему KG-RefMapEnsure
;; отличает пустую карту от несобранной.
;;
;; 72. Две сборки карты на крупном чертеже (366 с прогон) стоили 120 с --
;; почти треть. Причина не в обходе определений, а в KG-RefMapSet: на КАЖДОЕ
;; ребро он заново пересобирал весь список через KG-StrEq, то есть strcase на
;; каждое сравнение. Теперь сборка и правки идут точными сравнениями
;; (assoc/member/subst -- ключи приходят из чертежа в каноническом виде), а
;; сравнение без учёта регистра -- только запасной путь (KG-RMCdr, KG-RMSet).
;; Замер на 4000 рёбер и 400 имён: 11.2 с -> 0.5 с; KG-EXRefHolders
;; (1239 вставок, 250 имён): 2.0 с -> 0.06 с. Живой прогон подтвердил:
;; 366.5 с -> 251.4 с, сборка карты 120 с -> 14.75 с.
(if (not (boundp 'KG-REFREV)) (setq KG-REFREV nil))
(if (not (boundp 'KG-REFREV-ON)) (setq KG-REFREV-ON nil))
;; Пары «старое имя -> служебное», которые ещё не перепривязаны:
;; ((старое служебное) ...).
(if (not (boundp 'KG-REWPAIRS)) (setq KG-REWPAIRS nil))
;; Имена, чьи вставки оставлены как есть из-за риска зациклить определение.
(if (not (boundp 'KG-REWSKIP)) (setq KG-REWSKIP nil))

;; Состояния видимости вложенных блоков внутри определений, снятые ДО
;; освобождения имён: ((имя . ((вложенный . состояние) ...)) ...).
;; Подменяемое определение теряет состояния вложенных блоков -- они
;; сбрасываются в значения по умолчанию новой версии.
(if (not (boundp 'KG-NESTSAVE)) (setq KG-NESTSAVE nil))
(if (not (boundp 'KG-NESTSAVEN)) (setq KG-NESTSAVEN 0))
;; Сколько вложенных вставок при снятии осталось без состояния видимости.
(if (not (boundp 'KG-NESTDROP)) (setq KG-NESTDROP 0))

;; План интеграции (семейство, варианты, вложенные).
(if (not (boundp 'KG-PLAN)) (setq KG-PLAN nil))

;; 71.3: имена, которые обязана сохранить очистка, даже если на них никто
;; не ссылается: мастер-версии и определения вариантов текущего прогона.
;; Без этого PURGE "Блоки *" снимал мастер-версию с нулём вставок, и в
;; файле не оставалось ни мастера, ни варианта («мастер остаётся в файле»).
(if (not (boundp 'KG-KEEPNAMES)) (setq KG-KEEPNAMES nil))

;; 71.3: якорные вложения ((имя . ename) ...), которые держат имена
;; KG-KEEPNAMES "использованными" на время очистки. Живут внутри одного
;; прогона очистки; снимаются в KG-PurgeAnchorsDrop, в том числе по ошибке.
(if (not (boundp 'KG-PURGE-ANCHORS)) (setq KG-PURGE-ANCHORS nil))

;; 71.9: читать ли через COM состояния вложенных блоков внутри определений.
;; t (по умолчанию) -- читать как раньше. nil -- не читать вовсе: аварийный
;; обход для чертежа, на котором COM-чтение вложенных состояний роняет
;; AutoCAD (0xC0000005). Видно в отчёте RDBERR.
(if (not (boundp 'KG-NESTED-COM)) (setq KG-NESTED-COM t))

;; 71.9: кэш «имя определения -> уже прочитанные состояния вложенных
;; вставок». Один и тот же *U-экземпляр сканируется повторно на каждое своё
;; вхождение, а именно повторные COM-обходы уронили крупный чертёж. Живёт
;; одно чтение модели (сбрасывается в KG_DBGetModel) плюс начало прогона
;; (KG-SaveVars).
(if (not (boundp 'KG-SCAN-CACHE)) (setq KG-SCAN-CACHE nil))

;; 72.7: дорогие свойства вхождения (вложенная видимость, динамика,
;; аннотативность, атрибуты) нужны только вставкам своей семьи. У чужой
;; вставки они нигде не используются, а именно на них падал крупный
;; чертёж: семья 3 читала *U-представление ригеля семьи 2 (handle 93173)
;; и получала 0xC0000005.
;; KG-MODEL-FAMILY -- база семьи, для которой свойства читаются;
;; nil -- читать у всех (диагностика, одиночные вызовы).
;; KG-MODEL-SKIP-PROPS = t -- не читать дорогие свойства ни у кого
;; (снимки, где нужны только определения, имена и геометрия).
(if (not (boundp 'KG-MODEL-FAMILY)) (setq KG-MODEL-FAMILY nil))
(if (not (boundp 'KG-MODEL-SKIP-PROPS)) (setq KG-MODEL-SKIP-PROPS nil))

;; 71.9: журнал незавершённой команды. KG-JOURNAL-MINE = t -- журнал ведёт
;; ЭТА команда; nil -- в файле лежит улика прошлого падения, и KG-JournalErase
;; её не трогает. Подробности -- у KG-JournalWrite.
(if (not (boundp 'KG-JOURNAL-MINE)) (setq KG-JOURNAL-MINE nil))

;; 72.1. Перенос динамических свойств при замене экземпляров стоил 72.7 с
;; на 100 экземпляров (главный остаток живого прогона 72): KG_EXRestoreDynProps
;; на КАЖДОЕ сохранённое свойство заново перебирал весь список свойств
;; экземпляра и спрашивал имя по COM (D*P вызовов). Теперь карта «имя ->
;; свойство» собирается одним проходом (KG-RMSet/KG-RMCdr), а значения, уже
;; совпадающие с сохранёнными, не переписываются вовсе (KG-DynValEq): запись
;; динамического свойства запускает пересборку анонимного представления.
;;
;; 72.2. Живой прогон 72.1 на крупном чертеже: перенос свойств всё ещё около
;; 0.7 с на экземпляр (замена 100 экземпляров -- 80.1 с против 85.7 с в 72).
;; Карта имён почти ничего не стоит (0.00 с), а куда уходит остальное --
;; неизвестно: получение списка свойств, чтение текущих значений или сама
;; запись (она пересобирает анонимное представление блока). Добавлены
;; суб-замеры «вход», «чтение (работа)», «запись (работа)» и счётчики
;; «совпало», «записано», «не удалось», «попытки записи», «без пары».
;;
;; 72.3. Разбор падений 72.2 на крупном чертеже: оба прогона упали с
;; 0xC0000005 в чтении модели (KG-CollectInstances) -- после замены
;; экземпляров и на уже обработанном чертеже. Это не случайность: обход
;; вставок создаёт десятки тысяч COM-объектов, а падение ловится только
;; на больших чертежах. Поведение 72.2 не менялось -- добавлены только
;; диагностика и уборка:
;;   - обход вставок в чтении модели печатает каждые 100 вставок номер
;;     и handle: по протоколу видно, на какой вставке падение;
;;   - сборка мусора (gc) каждые 200 вставок, после 25 замен, перед
;;     тяжёлыми чтениями модели и после каждого семейства: отработанные
;;     COM-объекты освобождаются, не накапливаясь;
;;   - промежуточная таблица замеров печатается после каждого семейства,
;;     чтобы цифры сделанных семейств не терялись при падении на
;;     следующем.
(setq KG-VERSION "72.7")

(vl-load-com)

;;;===========================================================================
;;; РАЗДЕЛ 1. УТИЛИТЫ
;;;===========================================================================

(defun KG-RemoveAll (x lst)
  (vl-remove-if '(lambda (e) (equal e x)) lst)
)

;; Уникальные элементы с сохранением порядка
(defun KG-Unique (lst / out)
  (setq out nil)
  (foreach e lst
    (if (not (member e out)) (setq out (cons e out)))
  )
  (reverse out)
)

;; Сравнение строк без учёта регистра; nil трактуется как пустая строка
(defun KG-StrEq (a b)
  (= (strcase (KG-AsString a)) (strcase (KG-AsString b)))
)

;; Сравнение значений динамического свойства: текущего в новом экземпляре и
;; сохранённого у старого. Совпали -- писать не надо: запись свойства
;; запускает пересборку анонимного представления, а совпадение этого не
;; требует. nil и незнакомые типы совпадением НЕ считаются -- тогда значение
;; пишется, как раньше (это безопасный путь). Строки сравниваются без учёта
;; регистра (AutoCAD и так хранит каноническое написание), числа -- численно.
;; Чистая функция: живёт в утилитах рядом с KG-StrEq, чтобы стенд исполнял её
;; без AutoCAD (раздел 8 в тестовом режиме не загружается).
(defun KG-DynValEq (cur sav)
  (cond
    ((or (null cur) (null sav)) nil)
    ((and (numberp cur) (numberp sav)) (equal cur sav))
    ((and (= (type cur) 'STR) (= (type sav) 'STR)) (KG-StrEq cur sav))
    ((and (listp cur) (listp sav)) (equal cur sav))
    ((and (= (type cur) 'SYM) (= (type sav) 'SYM)) (eq cur sav))
    (t nil)
  )
)

;;; Число в строку для отчёта.
;;; (itoa nil) в AutoCAD -- это «неверный тип аргумента: fixnump: nil»;
;;; в отчёте такое недопустимо, поэтому все счётчики идут через неё.
(defun KG-NumStr (x)
  (itoa (fix (KG-AsNum x 0)))
)

;;; Приведение к строке.
;;; Из COM иногда приходит не строка, а variant или имя объекта; любая
;;; строковая функция на таком значении падает с "неверный тип аргумента:
;;; stringp". Одна точка приведения убирает этот класс ошибок целиком.
;; Метка шага: запоминается всегда, печатается только при (setq KG-TRACE t).
;; Если команда упадёт, обработчик ошибок назовёт объект, на котором это
;; случилось, -- поэтому метки стоят даже там, где печать не нужна.
(defun KG-Mark (s)
  (setq KG-LAST-STEP (KG-AsString s))
  (if KG-TRACE (princ (strcat "\n[шаг] " KG-LAST-STEP)))
)

;; Подробная печать шагов. KG-VERBOSE включается командами, KG-TRACE
;; пользователь ставит сам перед запуском -- (setq KG-TRACE t) -- когда
;; нужно увидеть каждый шаг. Без отдельного флага подробные метки
;; переполняли командную строку AutoCAD и хвост сообщения терялся.
(if (not (boundp 'KG-TRACE)) (setq KG-TRACE nil))
;; 71.4: замеры времени этапов прогона. Ставится до запуска:
;; (setq KG-TIMING t) -- строка на каждый шаг и сводка в конце команды.
(if (not (boundp 'KG-TIMING)) (setq KG-TIMING nil))
(defun KG-Trace (s)
  (setq KG-LAST-STEP (KG-AsString s))
  (if (or KG-VERBOSE KG-TRACE) (princ (strcat "\n[шаг] " KG-LAST-STEP)))
)

;;; Второй уровень трассировки: строки, которых на большом чертеже сотни.
;;;
;;; Повод -- переход на реципиента со 100 блоками. Один экземпляр даёт
;;; строку на каждое вложенное определение (их 83), на каждое поле
;;; вхождения (9) и на каждое определение в таблице (их больше 100). Лог
;;; не помещался в сообщение, и присылали только хвост -- а причина всегда
;;; оказывалась в начале.
;;;
;;; Последнее действие запоминается ВСЕГДА, даже когда строка не
;;; печатается: место падения по «Последний шаг» определяется и без
;;; подробной печати. Включается отдельно -- (setq KG-TRACE-DETAIL t).
(if (not (boundp 'KG-TRACE-DETAIL)) (setq KG-TRACE-DETAIL nil))
;;; Определения, которые ActiveX не отдал при чтении модели чертежа.
;;; Список, а не счётчик: имена нужны, чтобы понять, не потеряно ли
;;; среди них нужное вложенное определение.
(if (not (boundp 'KG-SKIP-DEFS)) (setq KG-SKIP-DEFS nil))
;;; Сколько определений прочитано в модель чертежа. Отдельная переменная,
;;; а не часть печатаемой строки: прогон сборки 57 показал, что строка из
;;; четырёх вызовов под одним перехватом не говорит, какой из них отказал.
(if (not (boundp 'KG-DEFCOUNT)) (setq KG-DEFCOUNT nil))
;;; Число прочитанных вхождений. Та же причина, что у KG-DEFCOUNT:
;;; значение хранится отдельно от строки, которая его печатает.
(if (not (boundp 'KG-INSTCOUNT)) (setq KG-INSTCOUNT nil))
;;; Получилось ли напечатать счётчик. Отдельный флаг, потому что условие
;;; по значению в LISP не работает: любое непустое значение истинно, и
;;; (not (KG-Safe ...)) не отличало отказ от успеха. Прогон сборки 58
;;; печатал предупреждение сразу после удачно напечатанного счётчика.
(if (not (boundp 'KG-CNT-OK)) (setq KG-CNT-OK nil))
;;; Обход карты ссылок на крупном чертеже: сколько объектов пройдено и
;;; кэш «handle владельца -> имя определения». Прогон на 1231 вставке
;;; оборвался с 0xC0000005, и без счётчика не было видно, дошёл ли обход
;;; до конца; а handent на каждом объекте -- лишний риск и лишняя работа.
(if (not (boundp 'KG-REFDONE)) (setq KG-REFDONE 0))
(if (not (boundp 'KG-REFCACHE)) (setq KG-REFCACHE nil))

;;; Шаг и причина ПОСЛЕДНЕГО отказа, перехваченного в KG-Safe.
;;; Отдельно от KG-LAST-STEP: тот перезаписывается каждым удачным шагом,
;;; и предупреждение, напечатанное позже, называло место, пройденное ДО
;;; отказа. Прогон сборки 56 читался именно так.
(if (not (boundp 'KG-LAST-STEP)) (setq KG-LAST-STEP nil))
(if (not (boundp 'KG-FAIL-STEP)) (setq KG-FAIL-STEP nil))
(if (not (boundp 'KG-FAIL-MSG)) (setq KG-FAIL-MSG nil))

;;; Текст причины отказа для предупреждения: шаг и сообщение вместе.
(defun KG-FailText ( / s)
  (setq s "")
  (if (and KG-FAIL-STEP (/= KG-FAIL-STEP ""))
    (setq s (strcat "шаг \"" KG-FAIL-STEP "\""))
  )
  (if (and KG-FAIL-MSG (/= KG-FAIL-MSG ""))
    (setq s (if (= s "") KG-FAIL-MSG (strcat s ", " KG-FAIL-MSG)))
  )
  (if (= s "") (setq s "(не записано)"))
  s
)
(defun KG-TraceDetail (s)
  (setq KG-LAST-STEP (KG-AsString s))
  (if KG-TRACE-DETAIL (princ (strcat "\n[шаг] " KG-LAST-STEP)))
)

(defun KG-AsString (x)
  (cond
    ((null x) "")
    ((= (type x) (type "")) x)
    ((= (type x) (type 0)) (itoa x))
    ((= (type x) (type 0.0)) (rtos x 2 6))
    (t (vl-catch-all-apply '(lambda () (vl-princ-to-string x))))
  )
)

;; Число ли значение. Проверяется только «явно число»: type у variant
;; возвращает nil, и любое сравнение с ним должно быть безопасно.
(defun KG-Num (x / t1 t2)
  (setq t1 (KG-Safe '(lambda () (type x)) nil))
  (setq t2 (KG-Safe '(lambda () (type 0)) nil))
  (if (or (and t1 t2 (equal t1 t2))
          (and t1 (equal t1 (KG-Safe '(lambda () (type 0.0)) nil))))
    t
    nil)
)

;;; Числовое приведение.
;;; itoa, rtos и арифметика в AutoCAD на nil падают с «неверный тип
;;; аргумента: fixnump: nil». Отдельная точка приведения убирает класс.
(defun KG-AsNum (x def / n)
  (setq n (if (KG-Num x) x nil))
  (if n n (if (KG-Num def) def 0.0))
)

;;; Список из значения COM: список остаётся списком, variant
;;; разворачивается через vlax-variant-value.
;;; ВАЖНО: (nth i variant) в AutoCAD даёт «неверный тип аргумента:
;;; consp #<variant …>» -- именно так падало чтение каждого вхождения.
;;; Поэтому nth к значениям COM здесь не применяется нигде.
(defun KG-ListValue (v / a n i out x)
  (cond
    ((or (null v) (KG-IsErr v)) nil)
    ((equal (KG-Safe '(lambda () (type v)) nil) (type (list nil))) v)
    (t
     (setq a (vl-catch-all-apply '(lambda () (vlax-variant-value v))))
     (if (KG-IsErr a)
       nil
       (progn
         (setq n (vl-catch-all-apply '(lambda () (vlax-safearray-get-u-bound a 1))))
         (if (not (KG-Num n))
           nil
           (progn
             (setq out nil i 0)
             (while (<= i n)
               (setq x (vl-catch-all-apply
                         '(lambda () (vlax-safearray-get-element a i))))
               (setq out (cons (if (KG-IsErr x) nil x) out))
               (setq i (1+ i))
             )
             (reverse out))))))
  )
)

;;; Точка (X Y Z) из значения COM. Всегда список из трёх чисел.
(defun KG-PointValue (v def / lst dx dy dz)
  (setq lst (KG-ListValue v))
  (if (or (null lst) (< (length lst) 3))
    (progn
      (setq lst (KG-ListValue def))
      (if (or (null lst) (< (length lst) 3))
        (list 0.0 0.0 0.0)
        (progn
          (setq dx (car lst))
          (setq dy (car (KG-Safe '(lambda () (cdr lst)) nil)))
          (setq dz (car (KG-Safe '(lambda () (cdr (cdr lst))) nil)))
          (list (KG-AsNum dx 0.0) (KG-AsNum dy 0.0) (KG-AsNum dz 0.0))))
    )
    (progn
      (setq dx (car lst))
      (setq dy (car (KG-Safe '(lambda () (cdr lst)) nil)))
      (setq dz (car (KG-Safe '(lambda () (cdr (cdr lst))) nil)))
      (list (KG-AsNum dx 0.0) (KG-AsNum dy 0.0) (KG-AsNum dz 0.0))
    )
  )
)

;;; Выполнить операцию; при ошибке -- запасное значение.
;;;
;;; ВАЖНО: сюда годится только КВОТИРОВАННАЯ лямбда '(lambda () ...) --
;;; она видит локальные переменные места вызова. Список-вызов сюда
;;; НЕЛЬЗЯ ни в каком виде: vl-catch-all-apply принимает первый
;;; аргумент как ФУНКЦИЮ, поэтому '(entdel e) и (list 'entdel e) -- это
;;; попытка вызвать список, ошибка, и запасное значение вместо
;;; результата. Если нужен вычисляемый вызов без лямбды -- звать
;;; vl-catch-all-apply напрямую: (vl-catch-all-apply 'entdel (list e)).
;;; Сборка 37 наступила на это: стирание *U отвечало nil при живом entdel.
;;; Последний шаг и причина последнего отказа объявляются ДО KG-Safe:
;;; ветка отказа читает KG-LAST-STEP, и без объявления первый же
;;; перехваченный отказ падал с «не определена переменная: KG-LAST-STEP».
(if (not (boundp 'KG-LAST-STEP)) (setq KG-LAST-STEP nil))
(if (not (boundp 'KG-FAIL-STEP)) (setq KG-FAIL-STEP nil))
(if (not (boundp 'KG-FAIL-MSG)) (setq KG-FAIL-MSG nil))

(defun KG-Safe (kg-fn kg-def / kg-res kg-msg)
  ;; У внутренних переменных приставка kg- НЕ для красоты: сюда приходят
  ;; лямбды, а у них подстановка динамическая -- свободная переменная
  ;; берётся из БЛИЖАЙШЕЙ рамки. Будь тут имена r, fn, def, msg, лямбда с
  ;; такой свободной переменной молча нашла бы их вместо своей. Так и
  ;; пропадал весь возврат ссылок -- разбор у KG-RewirePairOf.
  ;; Прошлый отказ сбрасывается ДО операции. Прогон сборки 58: строка
  ;; «[счёт] определений в списке: 57» напечаталась, а следом пошло
  ;; «ВНИМАНИЕ: не напечаталось число определений (шаг "счёт вхождений",
  ;; неверная функция: T), значение: 57» -- причина от одного отказа,
  ;; значение от другого, в одной строке.
  (setq KG-FAIL-STEP nil)
  (setq KG-FAIL-MSG nil)
  (setq kg-res (vl-catch-all-apply kg-fn))
  (if (KG-IsErr kg-res)
    (progn
      ;; Шаг, на котором произошёл отказ, запоминается ОТДЕЛЬНО.
      ;;
      ;; Прогон сборки 56: «ВНИМАНИЕ: снимок чертежа не прочитан (таблица
      ;; блоков прочитана)». Причина отказа печаталась как ПОСЛЕДНИЙ шаг,
      ;; но KG-Trace и KG-Mark перезаписывают KG-LAST-STEP на каждом
      ;; удачном шаге, поэтому к моменту печати там стоял шаг, прошедший
      ;; ДО отказа. Сообщение называло не то место и уводило в сторону.
      (setq KG-FAIL-STEP (KG-AsString KG-LAST-STEP))
      (setq kg-msg (KG-AsString
                     (vl-catch-all-apply
                       '(lambda () (vl-catch-all-error-message kg-res)))))
      (if (or (null kg-msg) (= kg-msg "")) (setq kg-msg "(причина не прочитана)"))
      (setq KG-FAIL-MSG kg-msg)
      kg-def
    )
    kg-res
  )
)

;;; Вызов с ВЫЧИСЛЯЕМЫМИ аргументами под перехватом. Отдельная функция
;;; потому, что KG-Safe принимает только лямбду: vl-catch-all-apply
;;; трактует первый аргумент как функцию, и список-вызов вместо вызова
;;; даёт ошибку и запасное значение.
(defun KG-Call (kg-fn kg-args kg-def / kg-res)
  (setq kg-res (vl-catch-all-apply kg-fn kg-args))
  (if (KG-IsErr kg-res) kg-def kg-res)
)

;;; Результат vl-catch-all-apply -- ошибка?
;;; Определена в разделе 1, а не в слое AutoCAD: утилиты приведения типов
;;; нужны и на тестовом стенде, где раздел 8 не загружается.
(defun KG-IsErr (x) (vl-catch-all-error-p x))

;;; Безопасный вариант проверки результата COM-вызова.
;;;
;;; (vl-catch-all-error-p) от живого vla-объекта на реальном чертеже сам
;;; бросает «неверная функция: T». Поэтому там, где на вход может прийти
;;; что угодно, проверку тоже надо перехватывать: иначе отказ проверки
;;; обрывает команду, и последняя метка указывает на уже пройденное место.
;;; Отказ проверки трактуется как «результат непригоден».
(defun KG-IsErrSafe (x def / r)
  (setq r (KG-Safe '(lambda () (vl-catch-all-error-p x)) def))
  r
)

;;;--- Замеры времени этапов (сборка 71.4) ------------------------------------
;;;
;;; Повод: на большом чертеже прогон идёт десятки секунд, и по отчёту не
;;; видно, что именно съедает время -- подготовка, интеграция семей или
;;; очистка. Метки шагов в прогонных функциях заменены на KG-MarkT: она
;;; делает всё, что KG-Mark, и вдобавок берёт время; при выключенном флаге
;;; расходов не остаётся.
;;;
;;; Включается до запуска: (setq KG-TIMING t). Время -- из системной
;;; переменной MILLISECS (миллисекунды); если её нет или значение не
;;; число (чужой интерпретатор), замеры молча выключаются и на прогон
;;; не влияют.
;;;
;;; KG-TSTART -- начало замера (KG-TimeReset в начале команды), KG-TSTAMP --
;;; время прошлой метки, KG-TLINES -- пары «метка . мс» для сводки.

(defun KG-NowMs ( / v)
  (setq v (KG-Safe '(lambda () (getvar "MILLISECS")) nil))
  (if (numberp v) (fix v) nil)
)

;; Миллисекунды в секунды для отчёта: 0.123. Флаг 2 в rtos -- десятичный
;; формат: точка одна и та же при любой локали.
(defun KG-SecStr (ms)
  (rtos (/ (* (fix ms) 1.0) 1000.0) 2 3)
)

(defun KG-TimeReset ()
  (setq KG-TSTART (KG-NowMs))
  (setq KG-TSTAMP KG-TSTART)
  (setq KG-TLINES nil)
  (setq KG-SUBT nil)
  (setq KG-SUBN nil)
)

(defun KG-TimeMark (kg-label / kg-ms kg-d kg-tot)
  ;; приставка kg- у имён не для красоты: сюда приходят вызовы из лямбд
  ;; KG-Safe, а у них подстановка динамическая -- свободное имя метки
  ;; могло бы найти чужую рамку (тот же урок, что у KG-Safe).
  (if KG-TIMING
    (progn
      (setq kg-ms (KG-NowMs))
      (if (and kg-ms KG-TSTART)
        (progn
          (setq kg-d (- kg-ms KG-TSTAMP))
          (setq kg-tot (- kg-ms KG-TSTART))
          (setq KG-TSTAMP kg-ms)
          (setq KG-TLINES (cons (cons (KG-AsString kg-label) kg-d) KG-TLINES))
          (princ (strcat "\n[время] " (KG-AsString kg-label) ": "
                         (KG-SecStr kg-d) " с (всего " (KG-SecStr kg-tot) ")"))
        )
      )
    )
  )
)

;; Сводка: шаги с временем и общий итог. Печатается в конце команд RDB,
;; RDBPICK и RDBCLEANUP; можно вызвать и вручную: (KG-TimeReport).
(defun KG-TimeReport ( / kg-ms kg-rec)
  (if KG-TIMING
    (progn
      (setq kg-ms (KG-NowMs))
      (if (null kg-ms)
        (princ "\n=== ЗАМЕРЫ ВРЕМЕНИ: переменная MILLISECS недоступна ===")
        (if (or KG-TLINES KG-TSTART)
          (progn
            (princ "\n=== ЗАМЕРЫ ВРЕМЕНИ (с) ===")
            (foreach kg-rec (reverse KG-TLINES)
              (princ (strcat "\n  " (car kg-rec) ": " (KG-SecStr (cdr kg-rec))))
            )
            (if KG-TSTART
              (princ (strcat "\n  ИТОГО прогон: " (KG-SecStr (- kg-ms KG-TSTART))))
            )
            ;; Суб-замеры: накопительные суммы по мелким шагам внутри
            ;; крупных этапов. Печатаются, только когда что-то накопилось.
            (if KG-SUBT
              (progn
                (princ "\n  -- суб-замеры (накопительно) --")
                (foreach kg-rec (reverse KG-SUBT)
                  (princ (strcat "\n  суб: " (car kg-rec) ": "
                                 (KG-SecStr (cdr kg-rec)) " с ("
                                 (itoa (KG-AsNum (KG-CdrCI (car kg-rec) KG-SUBN) 0))
                                 " выз.)"))
                )
              )
            )
          )
        )
      )
    )
  )
)

;; 72.3: промежуточный отчёт замеров после семейства и уборка мусора.
;; (gc) освобождает отработанные COM-объекты между семействами: на
;; крупном чертеже их накапливаются десятки тысяч, и чтение модели
;; может упасть с 0xC0000005. Отчёт печатается при KG-TIMING, чтобы
;; цифры уже сделанных семейств остались в протоколе и при падении
;; на следующем семействе.
(defun KG-FamilyReport (kg-note)
  (if (and (boundp 'KG-TIMING) KG-TIMING)
    (progn
      (princ (strcat "\n=== ЗАМЕРЫ ВРЕМЕНИ (промежуточные" kg-note ") ==="))
      (KG-TimeReport)
    )
  )
  (gc)
)

;; Метка шага с точкой замера. Поведение KG-Mark сохраняется полностью;
;; при выключенном KG-TIMING добавляется лишь один пустой вызов.
(defun KG-MarkT (s)
  (KG-Mark s)
  (KG-TimeMark s)
)

;; Суб-замеры: накопительная сумма времени по подписи подшага.
;; Нужны внутри этапов из сотни мелких вызовов, где одна метка не
;; говорит, что именно дорого. Копятся отдельно от журнала KG-TLINES и
;; печатаются строкой «суб: …» в KG-TimeReport. При выключенном
;; KG-TIMING или без MILLISECS это два дешёвых вызова.
(defun KG-SubAdd (kg-tag kg-dt)
  (if (and (boundp 'KG-TIMING) KG-TIMING kg-tag kg-dt)
    (progn
      (setq KG-SUBT
        (KG-SetAssoc (KG-AsString kg-tag)
                     (+ (KG-AsNum (KG-CdrCI (KG-AsString kg-tag) KG-SUBT) 0)
                        kg-dt)
                     KG-SUBT))
      ;; число вызовов рядом со временем: 0.5 с при 3 вызовах и при
      ;; 76 вызовах -- разные выводы.
      (setq KG-SUBN
        (KG-SetAssoc (KG-AsString kg-tag)
                     (1+ (KG-AsNum (KG-CdrCI (KG-AsString kg-tag) KG-SUBN) 0))
                     KG-SUBN))
    )
  )
)

;; Точки суб-замера: (KG-SubT1 "шаг" (KG-SubT0)). Без флага KG-SubT0
;; возвращает nil, и KG-SubT1 ничего не делает.
(defun KG-SubT0 ()
  (if (and (boundp 'KG-TIMING) KG-TIMING) (KG-NowMs) nil)
)
(defun KG-SubT1 (kg-tag kg-t0 / kg-t1)
  (if (and (boundp 'KG-TIMING) KG-TIMING kg-t0)
    (progn
      (setq kg-t1 (KG-NowMs))
      (if (and kg-t1 (>= kg-t1 kg-t0))
        (KG-SubAdd kg-tag (- kg-t1 kg-t0))
      )
    )
  )
)

;;;--- Журнал незавершённой команды (сборка 71.9) -----------------------------
;;
;; Жёсткое падение AutoCAD (0xC0000005) не ловится vl-catch-all-apply и не
;; вызывает *error*: команда обрывается, системные переменные остаются
;; изменёнными, а временные вложения защиты от PURGE -- в чертеже. Поэтому
;; перед работой на диск кладётся журнал, а следующая команда находит его и
;; доводит возврат до конца (KG-CrashRecover, команда RDBRECOVER).
;;
;; Здесь -- чистая часть: сборка и разбор строк журнала. Формат: одна
;; запись -- одна строка, поля разделены "|". Разделитель безопасен: символ
;; "|" запрещён в именах блоков AutoCAD, а значения системных переменных
;; целые. Проверяется тестами T32.
(defun KG-JournalEncode (kg-fields / kg-out kg-x)
  (setq kg-out "")
  (foreach kg-x kg-fields
    (setq kg-out (strcat kg-out (if (= kg-out "") "" "|")
                         (KG-AsString kg-x)))
  )
  kg-out
)

(defun KG-JournalSplit (kg-s / kg-out kg-b kg-i kg-n kg-ch)
  (setq kg-s (KG-AsString kg-s))
  (setq kg-out nil)
  (setq kg-b "")
  (setq kg-i 1)
  (setq kg-n (strlen kg-s))
  (while (<= kg-i kg-n)
    (setq kg-ch (substr kg-s kg-i 1))
    (if (= kg-ch "|")
      (progn
        (setq kg-out (cons kg-b kg-out))
        (setq kg-b "")
      )
      (setq kg-b (strcat kg-b kg-ch))
    )
    (setq kg-i (1+ kg-i))
  )
  (reverse (cons kg-b kg-out))
)

;; Строки файла -> записи (список списков полей). Пустые строки пропускаются.
(defun KG-JournalParse (kg-lines / kg-out kg-x)
  (setq kg-out nil)
  (foreach kg-x kg-lines
    (if (and kg-x (/= (KG-AsString kg-x) ""))
      (setq kg-out (cons (KG-JournalSplit kg-x) kg-out))
    )
  )
  (reverse kg-out)
)

;; Записи с указанным ключом (первое поле).
(defun KG-JournalRecs (kg-key kg-recs / kg-out kg-r)
  (setq kg-out nil)
  (foreach kg-r kg-recs
    (if (and kg-r (car kg-r) (KG-StrEq (car kg-r) kg-key))
      (setq kg-out (cons kg-r kg-out))
    )
  )
  (reverse kg-out)
)

;;; Логическое значение, пришедшее из COM.
;;;
;;; AutoCAD возвращает :vlax-true / :vlax-false, и ОБА этих символа в
;;; условии истинны: (if :vlax-false t nil) даёт T. Именно так каждое
;;; определение чертежа получало флаг «внешняя ссылка», KG-UserDefNames
;;; возвращал пустой список, и освобождать перед вставкой оказывалось
;;; нечего -- 40 вложенных определений оставались старыми.
(defun KG-ComBool (v / s)
  (cond
    ((null v) nil)
    ((KG-IsErr v) nil)
    (t
     (setq s (strcase (vl-princ-to-string v)))
     (cond
       ((= s ":VLAX-FALSE") nil)
       ((= s ":VLAX-TRUE") t)
       ((= (type v) (type 0)) (/= v 0))
       (t t)
     )
    )
  )
)

;;; Прочитать поле объекта; при ошибке -- запасное значение.
;;; Ни одно поле не должно ронять чтение всего экземпляра.
(defun KG-Field (obj prop def / r)
  (setq r (vl-catch-all-apply '(lambda () (vlax-get-property obj prop))))
  (if (or (KG-IsErr r) (null r)) def r)
)

;; Содержит ли строка подстроку (без учёта регистра)
(defun KG-StrContains (s sub / i n m)
  (setq s (KG-AsString s))
  (setq sub (KG-AsString sub))
  (if (= sub "")
    nil
    (progn
      (setq n (strlen s))
      (setq m (strlen sub))
      (setq i 1)
      (while (and (> i 0) (<= i (1+ (- n m))))
        (if (= (strcase (substr s i m)) (strcase sub))
          (setq i (- -1 i))                    ; нашли: выходим с i < 0
          (setq i (1+ i))
        )
      )
      (< i 0)
    )
  )
)

;; Позиция подстроки в строке (1-based, без учёта регистра), nil если не найдено
(defun KG-StrPos (sub s / i n m found)
  (setq s (KG-AsString s))
  (setq sub (KG-AsString sub))
  (if (or (= s "") (= sub ""))
    nil
    (progn
      (setq n (strlen s))
      (setq m (strlen sub))
      (setq i 1 found nil)
      (while (and (not found) (<= i (1+ (- n m))))
        (if (= (strcase (substr s i m)) (strcase sub))
          (setq found i)
          (setq i (1+ i))
        )
      )
      found
    )
  )
)

(defun KG-TrimLeft (s / n i)
  (setq s (KG-AsString s))
  (if (= s "") ""
    (progn
      (setq n (strlen s))
      (setq i 1)
      (while (and (<= i n) (= (substr s i 1) " ")) (setq i (1+ i)))
      (if (> i n) "" (substr s i))
    )
  )
)

(defun KG-TrimRight (s / n)
  (setq s (KG-AsString s))
  (if (= s "") ""
    (progn
      (setq n (strlen s))
      (while (and (> n 0) (= (substr s n 1) " ")) (setq n (1- n)))
      (if (= n 0) "" (substr s 1 n))
    )
  )
)

(defun KG-TrimBoth (s) (KG-TrimLeft (KG-TrimRight s)))

(defun KG-StrKey (s) (strcase (KG-AsString s)))

;; Разность списков строк без учёта регистра: a \ b
(defun KG-StrDiffCI (a b / out)
  (setq out nil)
  (foreach e a
    (if (not (vl-some '(lambda (x) (KG-StrEq e x)) b))
      (setq out (cons e out))
    )
  )
  (reverse out)
)

;; Пересечение списков строк без учёта регистра
(defun KG-StrInterCI (a b / out)
  (setq out nil)
  (foreach e a
    (if (vl-some '(lambda (x) (KG-StrEq e x)) b)
      (setq out (cons e out))
    )
  )
  (reverse out)
)

;; Поиск пары в списке ассоциаций по строковому ключу без учёта регистра
(defun KG-AssocCI (key alst)
  (vl-some '(lambda (p) (if (KG-StrEq (car p) key) p nil)) alst)
)

;; Значение по ключу. ВНИМАНИЕ: nil возвращается и когда ключа нет,
;; и когда значение равно nil. Для проверки наличия ключа -- KG-HasKeyCI.
(defun KG-CdrCI (key alst / p)
  (setq p (KG-AssocCI key alst))
  (if p (cdr p) nil)
)

;; Есть ли ключ в списке ассоциаций (работает и со значением nil)
(defun KG-HasKeyCI (key alst)
  (if (KG-AssocCI key alst) t nil)
)

;; Логический флаг: T только если ключ есть и его значение не nil
(defun KG-FlagCI (key alst / p)
  (setq p (KG-AssocCI key alst))
  (if (and p (cdr p)) t nil)
)

;; Замена или добавление пары в списке ассоциаций
(defun KG-SetAssoc (key val alst / out done)
  (setq out nil done nil)
  (foreach p alst
    (if (KG-StrEq (car p) key)
      (progn (setq out (cons (cons key val) out)) (setq done t))
      (setq out (cons p out))
    )
  )
  (if (not done) (setq out (cons (cons key val) out)))
  (reverse out)
)

;; Свободное имя, не занятое в списке used
(defun KG-UniqueName (prefix used / n cand)
  (setq n 0 cand prefix)
  (while (member (KG-StrKey cand) (mapcar 'KG-StrKey used))
    (setq n (1+ n))
    (setq cand (strcat prefix "$" (itoa n) "$"))
  )
  cand
)

;; Анонимное определение (*U, *D, *X, *E, *A ...)
(defun KG-IsAnonymousName (nm)
  (and nm (= (substr (KG-AsString nm) 1 1) "*"))
)

;; Системный блок AutoCAD: анонимный (*...), стрелка размера / выноски (_...)
;; или зависимый от внешней ссылки (*|*).
;; Такие блоки создаются и управляются самим AutoCAD, присутствуют в стилях
;; оформления и шаблонах (напр. _Oblique, _ArchTick, _Dot, _ClosedFilled,
;; _Origin, _Open, _Small, _None, _DetailView, _SectionView) и никогда не
;; должны переименовываться или включаться в список кандидатов на
;; освобождение имён.
(defun KG-IsSystemBlockName (nm / s)
  (setq s (KG-AsString nm))
  (and nm
       (or (= s "")
           (= (substr s 1 1) "*")
           (= (substr s 1 1) "_")
           (KG-StrContains s "|")
       )
  )
)

;; Анонимное представление динамического блока: *U и только цифры.
;; Именно такие определения держат на себе старые вложенные блоки и
;; при этом сами никем не вставлены. *Model_Space, *Paper_Space, *D
;; и *X под это определение не попадают.
(defun KG-IsAnonDynName (nm / s i ok)
  (setq s (KG-AsString nm))
  (setq ok (and (> (strlen s) 2) (KG-StrEq (substr s 1 2) "*U")))
  (setq i 3)
  (while (and ok (<= i (strlen s)))
    (if (KG-StrContains "0123456789" (substr s i 1))
      (setq i (1+ i))
      (setq ok nil)
    )
  )
  ok
)

;; Служебное имя, недопустимое в финальном результате (п. 20 ТЗ).
;; Имена вида "Стойка~~14" сюда НЕ входят: это осмысленное имя, под которым
;; сохраняется старое определение, и оно не маскируется под результат.
(defun KG-IsServiceName (nm)
  (and nm
       (or (KG-IsSystemBlockName nm)
           (wcmatch (strcase (KG-AsString nm))
                    "*$0$*,*$1$*,*$2$*,*_NEW,*-КОПИЯ")
       )
  )
)

;; Снять служебную отметку старого определения. Текущая сборка
;; переименовывает определение в «~ИМЯ» (при необходимости «~ИМЯ~итерация»,
;; а при занятом имени -- «~ИМЯ$N$»); прежние сборки -- в «ИМЯ~доитерация».
;; Обе формы поддерживаются: в чертежах, прошедших прежние сборки, старые
;; определения ещё остаются.
;;
;; Отметка снимается обязательно: определения переименовываются ДО чтения
;; старых экземпляров, поэтому вложенные вставки в них указывают уже на
;; «~Стойка КП50» («Стойка КП50~до» у прежних сборок), а в новом
;; определении вложенный блок называется «Стойка КП50». Без снятия отметки
;; ни одно состояние вложенного блока не переносилось: «В новой версии
;; такого вложенного блока нет».
(defun KG-StripDoSuffix (nm / s pos)
  (setq s (KG-AsString nm))
  (if (= (substr s 1 1) "~")
    (progn
      (setq s (substr s 2))
      (setq pos (KG-StrPos "~" s))
      (if pos (setq s (substr s 1 (1- pos))))
      (setq pos (KG-StrPos "$" s))
      (if pos (setq s (substr s 1 (1- pos))))
      s
    )
    (progn
      (setq pos (KG-StrPos "~до" s))
      (if pos
        (substr s 1 (1- pos))
        s
      )
    )
  )
)

;; Служебное (временное) имя старого определения: «~ИМЯ…» -- как
;; переименовывает текущая сборка, или «ИМЯ~до…» -- как переименовывали
;; прежние. Такое имя не настоящее: в разбор семейства не принимается,
;; а в очистке означает мусор прошлой интеграции.
(defun KG-IsTempDefName (nm / s)
  (setq s (KG-AsString nm))
  (if (or (= (substr s 1 1) "~")
          (/= nil (KG-StrPos "~до" s)))
    t
    nil
  )
)

;; Одно и то же вложение до переименования и после. Имя -- то, что стоит
;; в группе 2 вложенной вставки; эталон -- имя вложенного блока в новом
;; определении.
(defun KG-NestedKeyMatch (nm key)
  (or (KG-StrEq nm key)
      (KG-StrEq (KG-StripDoSuffix nm) (KG-StripDoSuffix key)))
)

(defun KG-Say (s)
  (if KG-REPORT-CAPTURE
    (setq KG-REPORT-BUF (cons (KG-AsString s) KG-REPORT-BUF))
  )
  (princ (strcat "\n" s))
)
(defun KG-SayKV (k v)
  (if KG-REPORT-CAPTURE
    (setq KG-REPORT-BUF
      (cons (strcat (KG-AsString k) ": " (KG-AsString v)) KG-REPORT-BUF))
  )
  (princ (strcat "\n" (KG-AsString k) ": " (KG-AsString v)))
)

(defun KG-VarLabel (v) (strcat "\"" (if v v "") "\""))

;; Склейка имён в одну строку для сообщений
(defun KG-JoinNames (names / out)
  (setq out "")
  (foreach n names
    (setq out (strcat out (if (= out "") "" ", ") n))
  )
  out
)

;;;===========================================================================
;;; РАЗДЕЛ 2. ПАРСЕР ИМЕНИ БЛОКА
;;;
;;; Поддерживаются две схемы именования.
;;;
;;; 1. Производственная (основная):  БАЗА vВЕРСИЯ ВАРИАНТ
;;;      "Комплект КП50 v1.5"                    -> база "Комплект КП50",
;;;                                                 итерация "1.5", вариант ""
;;;      "Комплект КП50К v1.5"                   -> база "Комплект КП50К"
;;;      "Комплект КП50 v1.21 стойка КП45302-1"  -> вариант "стойка КП45302-1"
;;;    Версия -- всегда "v" + цифры через точку: v1.1, v1.5, v1.21, v2.0.
;;;    Буква v не обязана быть отделена от базы, но ДОЛЖНА отделяться
;;;    пробелом от варианта; берётся ПОСЛЕДНЯЯ подходящая метка версии.
;;;
;;; 2. Из технического задания:  БАЗА(ИТЕРАЦИЯ)ВАРИАНТ
;;;      "ABC1.01(15)Стойка" -> база "ABC1.01", итерация "15", вариант "Стойка"
;;;    Разбирается ПОСЛЕДНЯЯ закрывающая скобка, поэтому
;;;    "A(1)(2)Стойка" -> база "A(1)", итерация "2", вариант "Стойка".
;;;
;;; Возвращает (list BASE ITER VARIANT) либо nil, если имя не подходит.
;;; ITER -- всегда строка ("1.5", "15"). VARIANT = "" для мастер-версии.
;;;===========================================================================

(defun KG-IsDigitChar (ch)
  (member ch '("0" "1" "2" "3" "4" "5" "6" "7" "8" "9"))
)

;; Позиция последнего вхождения подстроки sub в name, либо 0
(defun KG-LastPos (name sub / i n m res)
  (setq name (KG-AsString name))
  (setq n (strlen name))
  (setq m (strlen sub))
  (setq res 0)
  (setq i (1+ (- n m)))
  (while (> i 0)
    (if (and (= res 0) (= (strcase (substr name i m)) (strcase sub)))
      (setq res i)
    )
    (setq i (1- i))
  )
  res
)

;; Схема 1: БАЗА vВЕРСИЯ ВАРИАНТ
(defun KG-ParseVName (name / n i j k ch num base ver var)
  (setq n (strlen name))
  (setq i (KG-LastPos name " v"))
  (if (= i 0)
    nil
    (progn
      ;; i -- позиция пробела, метка версии начинается с i+1
      (setq j (+ i 2))                         ; первая цифра версии
      (if (or (> j n) (not (KG-IsDigitChar (substr name j 1))))
        nil
        (progn
          ;; читаем цифры и точки до конца версии
          (setq k j)
          (while (and (<= k n)
                      (or (KG-IsDigitChar (substr name k 1))
                          (= (substr name k 1) ".")))
            (setq k (1+ k))
          )
          (setq num (substr name j (- k j)))
          ;; версия не должна заканчиваться точкой
          (if (= (substr num (strlen num) 1) ".")
            nil
            (progn
              (setq base (substr name 1 (1- i)))
              (setq ver num)
              ;; вариант отделён от версии пробелом
              (setq var (if (> k n) "" (substr name (1+ k))))
              ;; после версии обязателен пробел, иначе "v1.21стойка"
              ;; было бы прочитано как версия 1.21 и вариант "стойка"
              (if (and (> (strlen var) 0) (= (substr var 1 1) " "))
                nil
                (list (KG-TrimRight base) ver (KG-TrimLeft var))
              )
            )
          )
        )
      )
    )
  )
)

;; Схема 2: БАЗА(ИТЕРАЦИЯ)ВАРИАНТ
(defun KG-ParseParenName (name / i n digits base iter var)
  (if (or (= name nil) (= name ""))
    nil
    (progn
      (setq n (strlen name))
      (setq i n)
      (while (and (> i 0) (/= (substr name i 1) ")"))
        (setq i (1- i))
      )
      (if (= i 0)
        nil                                    ; закрывающей скобки нет
        (progn
          (setq digits nil)
          (setq i (1- i))
          (while (and (> i 0) (KG-IsDigitChar (substr name i 1)))
            (setq digits (cons (substr name i 1) digits))
            (setq i (1- i))
          )
          (if (or (null digits) (< i 1) (/= (substr name i 1) "("))
            nil                                ; нет "(ЦИФРЫ)" перед ')' (или цифры дошли до начала имени)
            (progn
              (setq base (substr name 1 (1- i)))
              (setq iter (apply 'strcat digits))
              (setq var (substr name (+ i (length digits) 2)))
              (if (= base "")
                nil
                (list base iter var)
              )
            )
          )
        )
      )
    )
  )
)

(defun KG-ParseBlockName (name / p)
  (if (/= (type name) (type ""))
    nil                                        ; не строка -- разбирать нечего
    (if (KG-IsTempDefName name)
      nil                                      ; служебное имя старого определения
      (progn
        (setq p (KG-ParseVName name))            ; производственная схема
        (if (not p) (setq p (KG-ParseParenName name))) ; скобочная схема
        (if (not p)
          (if (and (/= (KG-TrimBoth name) "")
                   (not (KG-IsAnonymousName name))
                   (not (KG-IsSystemBlockName name))
                   (not (KG-IsServiceName name))
                   (not (KG-IsTempDefName name)))
            (setq p (list (KG-TrimBoth name) "" "")) ; простое имя без версии
          )
        )
        p
      )
    )
  )
)

(defun KG-ParseBase      (name / p) (setq p (KG-ParseBlockName name)) (if p (nth 0 p) nil))
(defun KG-ParseIteration (name / p) (setq p (KG-ParseBlockName name)) (if p (nth 1 p) nil))
(defun KG-ParseVariant   (name / p) (setq p (KG-ParseBlockName name)) (if p (nth 2 p) nil))

(defun KG-IsFamilyName (name base / p)
  (setq p (KG-ParseBlockName (KG-StripDoSuffix name)))
  (and p (KG-StrEq (nth 0 p) base))
)

(defun KG-IsIntegrationName (name base iter / p)
  (setq p (KG-ParseBlockName (KG-StripDoSuffix name)))
  (and p (KG-StrEq (nth 0 p) base) (KG-IterEq (nth 1 p) iter))
)

;;;--- Итерации ------------------------------------------------------------
;;; Итерация хранится строкой: "1.5" для производственной схемы, "15" для
;;; схемы ТЗ. Сравнивается по частям, поэтому v1.21 старше v1.5, а не наоборот.

;; Ключ для сравнения: части версии дополняются нулями до 6 разрядов,
;; поэтому обычное сравнение строк даёт правильный порядок.
(defun KG-IterKey (iter / s parts out p k i n first)
  ;; Номер итерации пишется без нуля на конце, когда он круглый:
  ;; v1.5 -- это итерация 50, v1.51 -- 51, v1.2 -- 20, v1.21 -- 21.
  ;; Значит, одноразрядная часть после точки означает десятки. Без
  ;; этого v1.5 (50) оказывалась старше v1.21 (21), потому что 5 < 21.
  ;; Первой части правило не касается: это номер версии, не итерация.
  ;; Побочное следствие: v1.5 и v1.50 -- одна и та же итерация 50.
  (setq s (if iter (KG-TrimBoth (strcase (KG-IterToStr iter))) ""))
  (if (= (substr s 1 1) "V") (setq s (substr s 2)))
  (setq parts (KG-SplitByDot s))
  (setq out "")
  (setq first t)
  (foreach p parts
    (setq i (atoi p))
    (if (and (not first) (= (strlen (KG-TrimBoth p)) 1))
      (setq i (* i 10))
    )
    (setq first nil)
    (setq k (itoa i))
    (setq n (strlen k))
    (while (< n 6) (setq k (strcat "0" k)) (setq n (1+ n)))
    (setq out (strcat out "." k))
  )
  out
)

(defun KG-SplitByDot (s / out cur i n ch)
  (setq out nil cur "" n (strlen s))
  (setq i 1)
  (while (<= i n)
    (setq ch (substr s i 1))
    (if (= ch ".")
      (progn (setq out (cons cur out)) (setq cur ""))
      (setq cur (strcat cur ch))
    )
    (setq i (1+ i))
  )
  (reverse (cons cur out))
)

;; Равенство итераций. Для схемы ТЗ сравниваем как числа, чтобы 05 и 5
;; считались одной итерацией; для версий -- по ключу.
;; Итерация в строку: может прийти и числом (схема ТЗ), и строкой версии
(defun KG-IterToStr (iter)
  (cond
    ((null iter) "")
    ((= (type iter) (type "")) iter)
    (t (itoa iter))
  )
)

(defun KG-IterEq (a b / sa sb ka kb)
  (setq sa (if a (KG-TrimBoth (KG-IterToStr a)) ""))
  (setq sb (if b (KG-TrimBoth (KG-IterToStr b)) ""))
  (if (and (= sa "") (= sb ""))
    t
    (if (or (= sa "") (= sb ""))
      nil
      (progn
        (setq ka (KG-IterKey sa))
        (setq kb (KG-IterKey sb))
        (if (and ka kb (= ka kb)) t nil)
      )
    )
  )
)

;; a строго старше b. Ключ -- строка, поэтому сравниваем посимвольно:
;; (< "…" "…") в AutoCAD падает с "неверный тип аргумента: fixnump".
(defun KG-IterOlder (a b)
  (KG-StrLt (KG-IterKey a) (KG-IterKey b))
)

;; Посимвольное сравнение строк: a строго меньше b.
;; Нужна потому, что операторы < > <= >= в AutoLISP числовые.
(defun KG-StrLt (a b / sa sb na nb i res found)
  (setq sa (KG-AsString a))
  (setq sb (KG-AsString b))
  (setq na (strlen sa))
  (setq nb (strlen sb))
  (setq i 1)
  (setq res nil)
  ;; found отдельным флагом: KG-CharLt может вернуть nil (a не меньше b),
  ;; и по одному res цикл не отличил бы «разница найдена» от «ещё идем»
  (setq found nil)
  (while (and (not found) (<= i na) (<= i nb))
    (if (= (substr sa i 1) (substr sb i 1))
      (setq i (1+ i))
      (progn
        (setq res (KG-CharLt (substr sa i 1) (substr sb i 1)))
        (setq found t)
      )
    )
  )
  ;; разница не найдена -- решает длина (префикс меньше)
  (if found res (< na nb))
)

;; Один символ строго меньше другого (по коду)
(defun KG-CharLt (a b)
  (< (KG-CharCode a) (KG-CharCode b))
)

;; Код символа (первый символ строки)
(defun KG-CharCode (s / n)
  (setq s (KG-AsString s))
  (setq n 1)
  (while (and (< n 65536) (/= (chr n) (substr s 1 1)))
    (setq n (1+ n))
  )
  (if (>= n 65536) 0 n)
)

;; a не совпадает с b -- этого достаточно, чтобы считать итерацию старой
(defun KG-IterOther (a b)
  (not (KG-IterEq a b))
)

;;; Сборка имени. Схема выбирается по виду итерации: с точкой -- значит
;;; производственная "БАЗА vВЕРСИЯ ВАРИАНТ", непустая без точки -- "БАЗА(ИТЕРАЦИЯ)ВАРИАНТ",
;;; пустая -- просто "БАЗА ВАРИАНТ" или "БАЗА".
(defun KG-MakeName (base iter var / s)
  (setq s (if iter (KG-TrimBoth (KG-IterToStr iter)) ""))
  (cond
    ((= s "")
     (if (and var (/= var "")) (strcat base " " var) base))
    ((KG-StrContains s ".")
     (strcat base " v" s (if (and var (/= var "")) (strcat " " var) "")))
    (t
     (strcat base "(" s ")" (if (and var (/= var "")) var "")))
  )
)

;;;--- Гибкий разбор семейства (сборка 71.3) ---------------------------------
;;;
;;; Заказчик принимает имя семейства в любом виде: и «Комплект КП50К стойка
;;; v1.52 КП45370», и прежний «Комплект КП50К стойка КП45370 v1.3». Отличие
;;; от KG-ParseBlockName: семейство известно заранее -- его называет
;;; пришедший мастер-блок. Метка версии поэтому ищется в любом месте
;;; хвоста имени, а остаток хвоста становится вариантом.

;; Имя начинается с «Комплект»: у таких семейств имена без метки версии
;; тоже считаются членами семьи («Комплект КП50»).
(defun KG-IsKomplektBase (b)
  (KG-StrEq (substr (KG-AsString b) 1 8) "Комплект")
)

;; s начинается с префикса b (без учёта регистра)? Возвращает остаток
;; строки (может быть пустым) или nil.
(defun KG-RestAfterPrefix (s b / ls lb)
  (setq ls (KG-AsString s))
  (setq lb (KG-AsString b))
  (if (<= (strlen lb) (strlen ls))
    (if (KG-StrEq (substr ls 1 (strlen lb)) lb)
      (substr ls (1+ (strlen lb)))
      nil
    )
    nil
  )
)

;; Последняя метка версии в строке: (позиция-v . "1.52") или nil. Метка --
;; " v" на границе слова, цифры и точки за ней, пробел или конец после;
;; точка на конце версии не считается. Ищется ПОСЛЕДНЯЯ ПОДХОДЯЩАЯ метка:
;; «A vZZ КП45370 v1.3» даёт 1.3, а не мусор посередине.
(defun KG-LastVerToken (s / i n n2 j k num lim found)
  (setq s (KG-AsString s))
  (setq n (strlen s))
  (setq lim n)
  (setq found nil)
  (while (and (null found) (> lim 1))
    (setq i (KG-LastPos (substr s 1 lim) " v"))
    (if (= i 0)
      (setq lim 1)
      (progn
        (setq n2 lim)
        (setq j (+ i 2))
        (if (or (> j n2) (not (KG-IsDigitChar (substr s j 1))))
          (setq lim (1- i))
          (progn
            (setq k j)
            (while (and (<= k n2)
                        (or (KG-IsDigitChar (substr s k 1))
                            (= (substr s k 1) ".")))
              (setq k (1+ k))
            )
            (setq num (substr s j (- k j)))
            (if (or (= num "")
                    (= (substr num (strlen num) 1) ".")
                    (and (< k n2) (/= (substr s k 1) " ")))
              (setq lim (1- i))
              (setq found (cons (1+ i) num))
            )
          )
        )
      )
    )
  )
  found
)

;; Разбор хвоста скобочной схемы «(16)КП7»: (iter . var) или nil.
;; KG-ParseParenName принимает только имя с базой, поэтому к хвосту
;; приставлена буква-заглушка.
(defun KG-TailParenScheme (tail / pt)
  (setq pt (KG-ParseParenName (strcat "x" tail)))
  (if (and pt (= (nth 0 pt) "x"))
    (cons (nth 1 pt) (nth 2 pt))
    nil
  )
)

;; Имя члена семьи base: (base итерация вариант) или nil, если имя к семье
;; не относится. После базы обязательна граница слова, поэтому «Комплект
;; КП50» не ловит «Комплект КП50К стойка». Метка версии -- в любом месте
;; хвоста; остаток хвоста -- вариант. Имя без версии -- тоже член семьи
;; (вариант целиком, итерация пустая).
(defun KG-FamilyParse (name base / s b tail t2 vt p ver pre post ts)
  (setq s (KG-AsString name))
  (setq b (KG-AsString base))
  (if (or (= b "") (= s "") (KG-IsTempDefName s))
    nil
    (progn
      (setq tail (KG-RestAfterPrefix s b))
      (if (not tail)
        nil
        (if (and (/= tail "") (/= (substr tail 1 1) " ")
                 ;; 71.3: схема KG-MakeName «БАЗА(16)ВАРИАНТ» пишется без
                 ;; пробела, поэтому «(» -- тоже граница слова, но лишь
                 ;; когда хвост и правда разбирается как (ЦИФРЫ)ВАРИАНТ
                 (not (and (= (substr tail 1 1) "(")
                           (KG-TailParenScheme tail))))
          nil                                  ; после базы не граница слова
          (progn
            (setq tail (KG-TrimBoth tail))
            (if (= tail "")
              (list b "" "")                   ; имя совпало с базой
              (progn
                (setq t2 (strcat " " tail))
                (setq vt (KG-LastVerToken t2))
                (if vt
                  (progn
                    (setq p (car vt))
                    (setq ver (cdr vt))
                    (setq pre (KG-TrimRight (substr t2 1 (- p 2))))
                    (setq post (KG-TrimLeft (substr t2 (+ p (strlen ver) 1))))
                    (list b
                          ver
                          (KG-TrimBoth (strcat pre
                                       (if (and (/= pre "") (/= post "")) " " "")
                                       post)))
                  )
                  (progn
                    (setq ts (KG-TailParenScheme tail))
                    (if ts
                      (list b (car ts) (cdr ts))   ; схема БАЗА(ИТЕРАЦИЯ)ВАРИАНТ
                      (list b "" tail)             ; вариант без версии
                    )
                  )
                )
              )
            )
          )
        )
      )
    )
  )
)

;; Активен ли гибкий разбор для семьи: пришёл версионный мастер и семья
;; «Комплект…». Без версии -- прежнее точное поведение (подмена
;; безверсионных мастер-блоков обязана работать как раньше).
(defun KG-FlexFamilyP (base newiter)
  (and (/= (KG-IterToStr newiter) "") (KG-IsKomplektBase base))
)

;; Разбор имени со снятой служебной отметкой «~ИМЯ»: разбор один и тот же
;; для определений и эффективных имён.
(defun KG-FamilyParseAny (name base / p)
  (setq p (KG-FamilyParse name base))
  (if (not p) (setq p (KG-FamilyParse (KG-StripDoSuffix name) base)))
  p
)

;;;===========================================================================
;;; РАЗДЕЛ 3. МОДЕЛЬ ЧЕРТЕЖА И СКАНИРОВАНИЕ
;;;
;;; model = (("defs" . (def ...)) ("insts" . (inst ...)) ("layouts" ...))
;;;
;;; def  = (("name" . "Имя") ("is-xref" . T/nil) ("is-layout" . T/nil)
;;;          ("is-dynamic" . T/nil) ("nested" . ("Имя1" ...))
;;;          ("vis-states" . ("A" "B")) ("vis-param" . "Видимость"))
;;;
;;; inst = (("handle" . "1F2") ("def" . "ИмяОпределения")
;;;          ("eff" . "ЭффективноеИмя") ("space" . "Model" | "Лист 1")
;;;          ("layer" . "0") ("pos" . (x y z)) ("rot" . 0.0)
;;;          ("sx" . 1.0) ("sy" . 1.0) ("sz" . 1.0) ("normal" . (0 0 1))
;;;          ("nested-vis" . (("Стойка" . "A"))) ("dyn-props" . (...)))
;;;===========================================================================

(defun KG-ModelDefs (model)    (cdr (assoc "defs" model)))
(defun KG-ModelInsts (model)   (cdr (assoc "insts" model)))
(defun KG-ModelLayouts (model) (cdr (assoc "layouts" model)))

(defun KG-FindDef (model name / hit)
  (setq hit nil)
  (foreach d (KG-ModelDefs model)
    (if (and (not hit) (KG-StrEq (KG-CdrCI "name" d) name)) (setq hit d))
  )
  hit
)

(defun KG-AllDefNames (model)
  (mapcar '(lambda (d) (KG-CdrCI "name" d)) (KG-ModelDefs model))
)

;; Пользовательские определения: не анонимные, не системные, не внешние ссылки, не листы
(defun KG-UserDefNames (model / out nm)
  (setq out nil)
  (foreach d (KG-ModelDefs model)
    (setq nm (KG-CdrCI "name" d))
    (if (and (not (KG-FlagCI "is-xref" d))
             (not (KG-FlagCI "is-layout" d))
             (not (KG-IsSystemBlockName nm)))
      (setq out (cons nm out))
    )
  )
  (reverse out)
)

;; Рекурсивно собрать вложенные определения (Этап 5).
;; Возвращает имена без дублей, не включая само root.
;; Анонимные и системные определения пропускаются, внешние ссылки -- тоже (п. 3.3 ТЗ).
(defun KG-GetNestedBlocks (model root / seen out)
  (setq seen (list (KG-StrKey root)))
  (setq out nil)
  (defun KG--Walk (mdl nm / def)
    (setq def (KG-FindDef mdl nm))
    (if def
      (foreach c (KG-CdrCI "nested" def)
        (if (and (not (KG-IsSystemBlockName c))
                 (not (member (KG-StrKey c) seen)))
          (progn
            (setq seen (cons (KG-StrKey c) seen))
            (setq out (cons c out))
            (KG--Walk mdl c)
          )
        )
      )
    )
  )
  (KG--Walk model root)
  (reverse out)
)

(defun KG-GetMasterDependencies (model mastername)
  (cons mastername (KG-GetNestedBlocks model mastername))
)

;; Все экземпляры семейства base во всём файле: (cons inst parsed)
(defun KG-FindFamilyInstances (model base / out p eff)
  (setq out nil)
  (foreach ins (KG-ModelInsts model)
    (setq eff (KG-CdrCI "eff" ins))
    (setq p (KG-ParseBlockName eff))
    (if (not p) (setq p (KG-ParseBlockName (KG-StripDoSuffix eff))))
    (if (and p (KG-StrEq (nth 0 p) base))
      (setq out (cons (cons ins p) out))
    )
  )
  (reverse out)
)

;; То же с гибким разбором (сборка 71.3): имя экземпляра разбирается от
;; известного семейства base.
(defun KG-FindFamilyInstancesFlex (model base / out p eff)
  (setq out nil)
  (foreach ins (KG-ModelInsts model)
    (setq eff (KG-CdrCI "eff" ins))
    (setq p (KG-FamilyParseAny eff base))
    (if p (setq out (cons (cons ins p) out)))
  )
  (reverse out)
)

;; Старые экземпляры: любое вхождение семейства с итерацией, отличной от
;;; новой (п. 5 ТЗ). Сравнение «меньше» здесь неприменимо: в чертеже может
;;; оказаться и более поздняя итерация, и её трогать нельзя.
;;; Для блоков без версии (newiter = ""):
;;; - если модель содержит переименованные определения («~ИМЯ», «~до»), старыми
;;;   считаются только они (а новое определение и его технический экземпляр -- новые);
;;; - если переименований ещё не было (исходная модель чертежа), все экземпляры
;;;   базового блока подлежат замене.
(defun KG-FindOldIterations (model base newiter / out any-do)
  (setq out nil)
  (if (KG-FlexFamilyP base newiter)
    ;; 71.3: гибкий разбор -- имя семейства в любом виде, остаток хвоста
    ;; вариант («Комплект КП50К стойка КП45370 v1.3» -- член семьи
    ;; «Комплект КП50К стойка» с вариантом «КП45370»).
    (foreach pr (KG-FindFamilyInstancesFlex model base)
      (if (KG-IterOther (nth 1 (cdr pr)) newiter)
        (setq out (cons pr out))
      )
    )
    (if (/= (KG-IterToStr newiter) "")
      (foreach pr (KG-FindFamilyInstances model base)
        (if (KG-IterOther (nth 1 (cdr pr)) newiter)
          (setq out (cons pr out)))
      )
      (progn
        (setq any-do
          (vl-some '(lambda (pr)
                      (or (KG-IsTempDefName (KG-CdrCI "def" (car pr)))
                          (KG-IsTempDefName (KG-CdrCI "eff" (car pr)))))
                   (KG-FindFamilyInstances model base)))
        (foreach pr (KG-FindFamilyInstances model base)
          (if (if any-do
                (or (/= (nth 1 (cdr pr)) "")
                    (KG-IsTempDefName (KG-CdrCI "def" (car pr)))
                    (KG-IsTempDefName (KG-CdrCI "eff" (car pr))))
                t)
            (setq out (cons pr out)))
        )
      )
    )
  )
  out
)

;; Определения семьи со старой версией -- в том числе те, у которых НЕТ ни
;; одной вставки: ((имя . (base вариант итерация)) ...). По ним видно, какие
;; варианты надо привести к новой версии, даже если на них никто не стоит
;; (правило «определения без вставок тоже обновлять»).
(defun KG-FindOldFamilyDefs (model base newiter / out nm p)
  (setq out nil)
  (foreach nm (KG-UserDefNames model)
    (setq p (KG-FamilyParse nm base))
    (if (and p (KG-IterOther (nth 1 p) newiter))
      (setq out (cons (cons nm p) out))
    )
  )
  (reverse out)
)

;; Группировка по варианту: (("Стойка" . (pr ...)) ("" . (pr ...)) ...)
(defun KG-GroupByVariant (pairs / keys out k)
  (setq keys nil)
  (foreach pr pairs
    (setq k (KG-StrKey (nth 2 (cdr pr))))
    (if (not (member k keys)) (setq keys (cons k keys)))
  )
  (setq keys (reverse keys))
  (setq out nil)
  (foreach k keys
    (setq out
      (cons
        (cons
          (vl-some '(lambda (pr)
                      (if (KG-StrEq (KG-StrKey (nth 2 (cdr pr))) k)
                        (nth 2 (cdr pr)) nil))
                   pairs)
          (vl-remove-if-not
            '(lambda (pr) (KG-StrEq (KG-StrKey (nth 2 (cdr pr))) k))
            pairs))
        out))
  )
  (reverse out)
)

(defun KG-FindOldVariants (groups) (mapcar 'car groups))

;; Сводка по пространствам: (("Model" . 13) ("Лист 1" . 6) ...)
(defun KG-CountBySpace (pairs / keys out k)
  (setq keys nil)
  (foreach pr pairs
    (setq k (KG-CdrCI "space" (car pr)))
    (if (not (member k keys)) (setq keys (cons k keys)))
  )
  (setq keys (reverse keys))
  (setq out nil)
  (foreach k keys
    (setq out
      (cons (cons k (length (vl-remove-if-not
                              '(lambda (pr) (equal (KG-CdrCI "space" (car pr)) k))
                              pairs)))
            out))
  )
  (reverse out)
)

;; Результат сканирования:
;;  family, newiter, groups, variants, spaces, total, iterations
(defun KG-ScanFamily (model base newiter / pairs groups its)
  (setq pairs (KG-FindOldIterations model base newiter))
  (setq groups (KG-GroupByVariant pairs))
  (setq its (KG-Unique (mapcar '(lambda (pr) (nth 1 (cdr pr))) pairs)))
  (setq its (vl-remove-if '(lambda (x) (= (KG-AsString x) "")) its))
  (list
    (cons "family" base)
    (cons "newiter" newiter)
    (cons "groups" groups)
    (cons "variants" (KG-FindOldVariants groups))
    (cons "spaces" (KG-CountBySpace pairs))
    (cons "total" (length pairs))
    ;; итерация -- строка версии ("1.5"), поэтому сортировка только
    ;; через сравнение ключей: (vl-sort its '<) падал с "fixnump: 1.5".
    ;; Функции sort в AutoCAD НЕТ -- есть vl-sort, vl-sort-i и
    ;; acad_strlsort; на реальном чертеже (sort ...) дал
    ;; "no function definition: SORT".
    (cons "iterations" (if its (vl-sort its 'KG-IterOlder) nil))
  )
)

;;;===========================================================================
;;; РАЗДЕЛ 4. ПЛАНИРОВАНИЕ ИНТЕГРАЦИИ
;;;===========================================================================

;; Карта вложенных определений (Этап 6):
;;   to-update -- имя есть и в мастер-версии, и в файле
;;   to-add    -- имя есть только в мастер-версии
(defun KG-MapNestedBlocks (model mastername / newnested existing)
  (setq newnested (KG-GetNestedBlocks model mastername))
  (setq existing (KG-UserDefNames model))
  (list
    (cons "to-update" (KG-StrInterCI newnested existing))
    (cons "to-add"    (KG-StrDiffCI  newnested existing))
  )
)

;;; Интерфейс ObjectDBX: невидимый документ в памяти, без файла на диске.
;; Одна попытка получить ObjectDBX двумя способами. Причина отказа
;; запоминается: без неё «ObjectDBX недоступен» -- это guesswork, а не
;; диагноз.
(defun KG-ObjectDbxTry (progid / app r)
  (setq app (vlax-get-acad-object))
  (setq r (vl-catch-all-apply 'vla-GetInterfaceObject (list app progid)))
  (if (KG-IsErr r)
    (progn
      (setq KG-DBX-ERR
        (cons (strcat progid " / GetInterfaceObject: "
                      (KG-AsString (vl-catch-all-error-message r)))
              KG-DBX-ERR))
      (setq r (vl-catch-all-apply 'vlax-create-object (list progid)))
      (if (KG-IsErr r)
        (progn
          (setq KG-DBX-ERR
            (cons (strcat progid " / create-object: "
                          (KG-AsString (vl-catch-all-error-message r)))
                  KG-DBX-ERR))
          nil
        )
        r
      )
    )
    r
  )
)

(defun KG-ObjectDbx ( / vrs dbx)
  (setq KG-DBX-ERR nil)
  (setq vrs (atoi (getvar "ACADVER")))
  (setq dbx (KG-ObjectDbxTry (strcat "ObjectDBX.AxDbDocument." (itoa vrs))))
  (if (not dbx)
    (setq dbx (KG-ObjectDbxTry "ObjectDBX.AxDbDocument"))
  )
  dbx
)

;; Что стало с определением мастер-версии после вставки из буфера.
;;
;; PASTECLIP молча игнорирует конфликтующее определение («Duplicate
;; definition of block ... ignored») и оставляет в чертеже СТАРОЕ. Тогда
;; вся интеграция идёт от устаревшего мастера, а по числу «пришло N»
;; этого не видно. Различаются три исхода:
;;   имени не было в чертеже      -- определение пришло новым;
;;   имя было и определение пришло -- старое перезаписано;
;;   имя было, но не пришло       -- мастер ОСТАЛСЯ СТАРЫМ.
;; Записать причину отказа в KG-DBX-ERR. Без этого «ObjectDBX недоступен»
;; не отличить от «интерфейс получен, но CopyObjects отказал».
;; Определения, которые можно удалить: ссылок нет, имя либо служебное
;; («~ИМЯ», у прежних сборок «~до»), либо разбирается схемой семейства и
;; не является новейшей итерацией.
;; Число ссылок по карте держателей: длина списка = количество вставок.
(defun KG-CleanupCounts (holders / out p)
  ;; Первый элемент может быть маркером успешной выборки ("OK"): карта
  ;; ссылок возвращается парой (маркер . карта), а пересчёт делается в
  ;; четырёх местах KG-CleanupRun, и в трёх из них маркер в сборке 39 не
  ;; снимался -- (length "OK") дал «неверный тип аргумента: consp "OK"»
  ;; сразу после стирания сиротских *U. Поэтому маркер отсекается здесь,
  ;; а не в каждом месте вызова.
  (if (KG-StrEq (KG-AsString (car holders)) "OK") (setq holders (cdr holders)))
  (setq out nil)
  (foreach p holders
    (setq out (KG-SetAssoc (car p) (length (cdr p)) out))
  )
  out
)

(defun KG-CleanupCandidates (counts names keep / cand nm c p)
  ;; Анонимные определения (*U, *Model_Space, *D...) в кандидаты не
  ;; попадают никогда. Сиротское *U можно снять только PURGE: у живого
  ;; экземпляра динамического блока представление называется тем же
  ;; *U133, а отличить одно от другого без COM-чтения EffectiveName
  ;; нельзя, а оно на этом чертеже роняет AutoCAD.
  (setq cand nil)
  (foreach nm names
    (setq c (KG-AsNum (KG-CdrCI nm counts) 0))
    (setq p (KG-ParseBlockName nm))
    (if (and (< c 1)
             (not (KG-IsAnonymousName nm))
             (or (KG-IsTempDefName nm)
                 (and p (/= (nth 1 p) "") (not (KG-StrInterCI (list nm) keep)))))
      (setq cand (cons nm cand))
    )
  )
  (reverse cand)
)

;; Сиротские анонимные представления: их никто не вставляет, но они
;; держат на себе старые вложенные определения. Программа их не удаляет,
;; только показывает -- их снимает PURGE.
(defun KG-CleanupOrphans (counts names / out nm)
  ;; то же, что в KG-CleanupCounts: список может прийти с маркером
  (if (KG-StrEq (KG-AsString (car counts)) "OK") (setq counts (cdr counts)))
  (setq out nil)
  (foreach nm names
    (if (and (KG-IsAnonDynName nm)
             (< (KG-AsNum (KG-CdrCI nm counts) 0) 1))
      (setq out (cons nm out))
    )
  )
  (reverse out)
)

;; Ключ -- семейство И вариант, а не одно семейство: «Комплект КП50 v1.51»
;; и «Комплект КП50 v1.51 КП45387» принадлежат одному семейству и одной
;; итерации, но это два разных определения, и защищать надо оба.
(defun KG-CleanupKeepNewest (names / keep p k hit)
  (setq keep nil)
  (foreach nm names
    (setq p (KG-ParseBlockName nm))
    (if (and p (/= (nth 1 p) ""))
      (progn
        (setq k (strcat (nth 0 p) "|" (nth 2 p)))
        (setq hit (KG-AssocCI k keep))
        (if (not hit)
          (setq keep (cons (cons k nm) keep))
          (if (KG-IterOlder (nth 1 (KG-ParseBlockName (cdr hit))) (nth 1 p))
            (setq keep (KG-SetAssoc k nm keep))
          )
        )
      )
    )
  )
  (mapcar 'cdr keep)
)

;; 71.3. Что очистка обязана сохранить сверх «последней версии каждого
;; варианта»: имена семьи без версии (у «Комплект…» они -- определения той
;; же семьи) и всё, что отмечено прогоном интеграции (KG-KEEPNAMES:
;; мастер-версии и определения вариантов).
(defun KG-CleanupKeepExtra (names / keep nm p nmver)
  (setq keep nil)
  (foreach nm names
    (setq p (KG-ParseBlockName nm))
    ;; имя без версии и без варианта с приставкой «Комплект» -- и в файле
    ;; есть другое имя этой же семьи (с версией или с вариантом)
    (if (and p (= (nth 1 p) "") (= (nth 2 p) "")
             (KG-IsKomplektBase nm)
             (vl-some '(lambda (x)
                         (if (KG-RestAfterPrefix x nm)
                           (progn
                             (setq nmver (KG-ParseBlockName x))
                             (and nmver (or (/= (nth 1 nmver) "")
                                            (/= (nth 2 nmver) ""))))
                           nil))
                      names))
      (setq keep (cons nm keep))
    )
  )
  (foreach nm KG-KEEPNAMES
    (if (not (KG-StrInterCI (list nm) keep))
      (setq keep (cons nm keep))
    )
  )
  (reverse keep)
)

;; Полный список имён, защищённых от очистки (кандидаты + PURGE).
(defun KG-CleanupKeepAll (names)
  (append (KG-CleanupKeepNewest names) (KG-CleanupKeepExtra names))
)

;; Пары «настоящее имя -> служебное» для возврата ссылок при очистке.
;; Ссылки на служебные определения живут внутри чужих определений и
;; анонимных представлений; пока их не вернуть на настоящие имена, ни
;; PURGE, ни стирание определения не берут -- оно «использовано», и
;; очистка не доходит до конца. Настоящее имя восстанавливается снятием
;; отметки (KG-StripDoSuffix): «~ИМЯ», «~ИМЯ~итерация», «~ИМЯ$N$»,
;; «ИМЯ~до…». Пара берётся только тогда, когда настоящее определение в
;; чертеже есть: если буфер имя не принёс, возвращать ссылку некуда, и
;; трогать её нельзя.
(defun KG-CleanupRestorePairs (names / out nm base)
  (setq out nil)
  (foreach nm names
    (if (KG-IsTempDefName nm)
      (progn
        (setq base (KG-StripDoSuffix nm))
        (if (and base (/= base "")
                 (not (KG-StrEq base (KG-AsString nm)))
                 (KG-StrInterCI (list base) names))
          (setq out (cons (list base nm) out))
        )
      )
    )
  )
  (reverse out)
)

;; Число отказов названной причины в списке причин KG_EXEraseAnonDef.
(defun KG-WhyCount (why al / v)
  (setq v (KG-CdrCI (KG-AsString why) al))
  (KG-AsNum v 0)
)

;; 71.8 / 72.4. Перепривязка паспортов динамики.
;;
;; Паспорт вставки -- расширенный словарь: AcDbBlockRepresentation ->
;; AcDbRepData -> объект ACDB_BLOCKREPRESENTATION_DATA с жёсткой ссылкой
;; (340) на запись BLOCK_RECORD базового определения. По паспорту AutoCAD
;; показывает настоящее имя вложенного динамического блока. На записях
;; анонимных представлений (*U) есть и xdata AcDbBlockRepBTag (1005).
;;
;; Определения-кандидаты к удалению («~имя» и остатки) могут держаться не
;; именами, а сетью динамики: по имени на них не ссылается никто, а ссылки
;; 340 из паспортов держат их записи «использованными», и PURGE их не
;; удаляет.
;;
;; Сборки до 72.4 в этом месте СНИМАЛИ деревья словарей у вставок внутри
;; определений (tblnext + entnext): дети стирались (entdel), записи словаря
;; удалялись (dictremove), корень оставался пустой оболочкой. Кандидаты
;; освобождались, НО паспорта живых вставок рвались: имя базового
;; определения переставало разрешаться, и в Свойствах оставалось «*U462»
;; вместо «Стойка КП50» (разбор -- пробы 462-468, 2026-10).
;;
;; 72.4. Деревья не снимаются: ссылки 340 переводятся на записи действующих
;; одноимённых определений (KG-RepTreeRepoint). Кандидат без замены остаётся
;; как есть -- лучше подержать старую запись, чем оборвать живой паспорт;
;; такие вставки называются в отчёте. Проверено живьём: entmod переставляет
;; 340 у объекта ACDB_BLOCKREPRESENTATION_DATA (проба 476), паспорт читается
;; обратно.

;; Записи BLOCK_RECORD для имён-кандидатов к удалению.
(defun KG-CleanupRepRecords (cand / out nm r)
  (setq out nil)
  (foreach nm cand
    (setq r (KG-Safe '(lambda () (cdr (assoc 330 (entget (tblobjname "BLOCK" nm))))) nil))
    (if r (setq out (cons r out)))
  )
  out
)

;; Есть ли x в списке L. Сравнение eq (не "="): в AutoCAD 2023 "=" на
;; ename возвращает nil даже для одной сущности (живая проба probe16),
;; а eq сравнивает по сущности.
(defun KG-RepMemEq (x L)
  (if (null L) nil (if (eq x (car L)) T (KG-RepMemEq x (cdr L))))
)

;; Ссылается ли объект o жёсткой ссылкой на одну из записей S.
;; Коды ссылок: 330 (владелец), 331 (BLKREFS), 340 (rep-data -> запись),
;; 350/360 (дети словаря), 1005 (xdata-тег динамики). Списочные значения
;; отсеиваются через listp (ename в AutoCAD -- не список): так же
;; устроена проверенная проба probe13.
(defun KG-RepRefHit (o S / el r pr)
  (setq r nil)
  (setq el (KG-Safe '(lambda () (entget o (list "*"))) nil))
  (if el
    (foreach pr el
      (if (and (not (listp (cdr pr)))
               (member (car pr) (list 330 331 340 350 360 1005))
               (KG-RepMemEq (cdr pr) S))
        (setq r T)
      )
    )
  )
  r
)

;; Есть ли в дереве словаря d (или ниже) ссылка на записи S. Глубина
;; ограничена: у динамических вставок словари глубже не встречались.
(defun KG-RepTreeHas (d S dep / lst r kid kt pr)
  (setq r nil)
  (if (< dep 5)
    (progn
      (setq lst (KG-Safe '(lambda () (entget d)) nil))
      (if lst
        (progn
          (if (KG-RepRefHit d S) (setq r T))
          (foreach pr lst
            (if (and (member (car pr) (list 350 360))
                     (not (listp (cdr pr))))
              (progn
                (setq kid (cdr pr))
                (setq kt (cdr (assoc 0 (KG-Safe '(lambda () (entget kid)) nil))))
                (if (= kt "DICTIONARY")
                  (if (KG-RepTreeHas kid S (1+ dep)) (setq r T))
                  (if (KG-RepRefHit kid S) (setq r T))
                )
              )
            )
          )
        )
      )
    )
  )
  r
)

;; 72.4. Замена для записи old в парах (запись . замена) или nil.
;; Сравнение -- eq (KG-RepMemEq): в AutoCAD 2023 "=" на ename возвращает nil
;; даже для одной и той же сущности.
(defun KG-RepPairNew (old pairs)
  (if (null pairs)
    nil
    (if (eq old (car (car pairs)))
      (cdr (car pairs))
      (KG-RepPairNew old (cdr pairs))
    )
  )
)

;; 72.4. Есть ли в списке объекта (entget) ссылка 340 на одну из записей olds.
(defun KG-RepHasOld340 (lst olds / hit)
  (setq hit nil)
  (foreach pr lst
    (if (and (= (car pr) 340)
             (not (listp (cdr pr)))
             (KG-RepMemEq (cdr pr) olds))
      (setq hit T)
    )
  )
  hit
)

;; 72.4. Перепривязка паспорта: в дереве словаря d заменить ссылки 340 со
;; старых записей на новые из пар (запись . замена). Дерево НЕ снимается --
;; именно снятие ломало имена живых вложенных динамических блоков. Дети
;; словарей обходятся как у KG-RepTreeHas; объект со ссылкой правится на
;; месте (entmod). Возврат: сколько ссылок перепривязано (0 -- не тронуто).
(defun KG-RepTreeRepoint (d pairs dep / lst n pr kid ed new olds)
  (setq n 0)
  (if (and d (< dep 6))
    (progn
      (setq olds (mapcar 'car pairs))
      (setq lst (KG-Safe '(lambda () (entget d)) nil))
      (if (and lst olds (KG-RepHasOld340 lst olds))
        (progn
          (setq ed nil)
          (foreach pr lst
            (if (and (= (car pr) 340) (not (listp (cdr pr))))
              (progn
                (setq new (KG-RepPairNew (cdr pr) pairs))
                (setq ed (cons (if new (cons 340 new) pr) ed))
              )
              (setq ed (cons pr ed))
            )
          )
          (setq ed (reverse ed))
          (if (KG-Safe '(lambda () (entmod ed)) nil)
            (setq n (1+ n))
          )
        )
      )
      (if lst
        (foreach pr lst
          (if (and (member (car pr) (list 350 360))
                   (not (listp (cdr pr))))
            (progn
              (setq kid (cdr pr))
              (if kid
                (setq n (+ n (KG-RepTreeRepoint kid pairs (1+ dep))))
              )
            )
          )
        )
      )
    )
  )
  n
)

;; 72.4. Проход по всем определениям таблицы блоков: у вставок, паспорт
;; которых ссылается на записи кандидатов, ссылки 340 переводятся на записи
;; действующих одноимённых определений (KG-RepTreeRepoint). Паспорта живых
;; вставок сохраняются. Если действующего имени нет («~имя» без замены),
;; паспорт не трогается, вставка называется в отчёте. Возврат -- список:
;; (перепривязано ссылок, вставок с перепривязкой, вставок без замены).
(defun KG-CleanupRepRepoint (cand / pairs norec nfix nins nleft tb nm blk e el xd f recold recnew base)
  (setq pairs nil norec nil nfix 0 nins 0 nleft 0)
  (foreach nm cand
    (setq recold (KG-Safe '(lambda () (cdr (assoc 330 (entget (tblobjname "BLOCK" nm))))) nil))
    (setq base (KG-Safe '(lambda () (KG-StripDoSuffix nm)) nil))
    (setq recnew (if (and base (/= (KG-AsString base) "")
                          (not (KG-StrEq base nm)))
                   (KG-Safe '(lambda () (cdr (assoc 330 (entget (tblobjname "BLOCK" base))))) nil)
                   nil
                 )
    )
    (if (and recold recnew (not (eq recold recnew)))
      (setq pairs (cons (cons recold recnew) pairs))
      (if recold (setq norec (cons recold norec)))
    )
  )
  (if pairs
    (progn
      (setq tb (KG-Safe '(lambda () (tblnext "BLOCK" T)) nil))
      (while tb
        (setq nm (cdr (assoc 2 tb)))
        (setq blk (KG-Safe '(lambda () (tblobjname "BLOCK" nm)) nil))
        (if blk
          (progn
            (setq e (KG-Safe '(lambda () (entnext blk)) nil))
            (while (and e (not (KG-StrEq (KG-AsString (cdr (assoc 0 (KG-Safe '(lambda () (entget e)) nil)))) "ENDBLK")))
              (setq el (KG-Safe '(lambda () (entget e (list "*"))) nil))
              (setq xd (if el (cdr (assoc 360 el)) nil))
              (if xd
                (progn
                  (setq f (KG-Safe '(lambda () (KG-RepTreeRepoint xd pairs 0)) 0))
                  (if (and f (> (KG-AsNum f 0) 0))
                    (progn
                      (setq nfix (+ nfix (KG-AsNum f 0)))
                      (setq nins (1+ nins))
                      (KG-TraceDetail
                        (strcat "паспорт динамики: \"" (KG-AsString nm)
                                "\" (" (KG-AsString (cdr (assoc 5 el))) ") перепривязан")
                      )
                    )
                    (if (and norec (KG-RepTreeHas xd norec 0))
                      (setq nleft (1+ nleft))
                    )
                  )
                )
              )
              (setq e (KG-Safe '(lambda () (entnext e)) nil))
            )
          )
        )
        (setq tb (KG-Safe '(lambda () (tblnext "BLOCK")) nil))
      )
    )
  )
  (if (and KG-TRACE-DETAIL (> (+ nfix nleft) 0))
    (princ (strcat "\nпаспорта динамики: перепривязано ссылок=" (itoa nfix)
                   ", вставок=" (itoa nins) ", без замены=" (itoa nleft)))
  )
  (list nfix nins nleft)
)

;;;--- 72.4. Лечение паспортов представлений (RDBHEAL) -----------------------
;;;
;;; Лечение нужно чертежам, испорченным сборками до 72.4: уборка снимала
;;; паспорта у вставок внутри определений, и имя вложенного динамического
;;; блока переставало разрешаться -- в Свойствах показывалось «*U462» вместо
;;; «Стойка КП50». Строение паспорта и механика записи -- в разборе 71.8/72.4
;;; выше. Здоровые паспорта не трогаются: пишется только недостающее.
;;;
;;; База ищется в два шага:
;;;   1) карта чертежа: по всем определениям и пространствам собраны пары
;;;      «представление -> имя базы» у вставок со здоровым паспортом;
;;;   2) «близнец»: определение с таким же строением (типы детей и имена,
;;;      а имена представлений считаются одинаковыми), у которого на том же
;;;      месте стоит здоровый ребёнок-представление; строение тела ребёнка
;;;      сверяется с близнецом нормализованно; при неоднозначности
;;;      (несколько разных баз) паспорт не пишется.
;;; Проверено живьём (проба 475): 36 из 36 повреждённых паспортов большого
;;; чертежа вылечены, чтение после переоткрытия подтвердило имена, AUDIT
;;; чистый.

;; Имя представления (*U...).
(defun KG-RepHealIsRep (nm)
  (and nm (> (strlen nm) 2) (KG-StrEq (substr nm 1 2) "*U"))
)

;; Токен объекта для сверки строения: "I:имя" для вставки, иначе тип.
(defun KG-RepHealTok (ed / ty)
  (setq ty (KG-AsString (cdr (assoc 0 ed))))
  (if (KG-StrEq ty "INSERT")
    (strcat "I:" (KG-AsString (cdr (assoc 2 ed))))
    ty
  )
)

;; Токен строения с нормализацией имён представлений (все *U -- как один).
(defun KG-RepHealNormTok (tok / nm)
  (if (and (> (strlen tok) 2) (KG-StrEq (substr tok 1 2) "I:"))
    (progn
      (setq nm (substr tok 3))
      (if (KG-RepHealIsRep nm) "*U" tok)
    )
    tok
  )
)

;; Строение тела определения (сортированные токены; нормализация *U).
(defun KG-RepHealSorted (ents)
  (vl-sort (mapcar '(lambda (x) (KG-RepHealNormTok (car x))) ents) '<)
)

;; Тело определения: список пар (токен . ename) по объектам в порядке.
(defun KG-RepHealEnts (nm / blk e ed lst)
  (setq lst nil)
  (setq blk (KG-Safe '(lambda () (tblobjname "BLOCK" nm)) nil))
  (if blk
    (progn
      (setq e (KG-Safe '(lambda () (entnext blk)) nil))
      (while (and e
                  (not (KG-StrEq (KG-AsString
                                   (cdr (assoc 0 (KG-Safe '(lambda () (entget e)) nil))))
                                  "ENDBLK")))
        (setq ed (KG-Safe '(lambda () (entget e)) nil))
        (if ed (setq lst (cons (cons (KG-RepHealTok ed) e) lst)))
        (setq e (KG-Safe '(lambda () (entnext e)) nil))
      )
    )
  )
  (reverse lst)
)

;; Имя блока, на который ссылается вставка (или "").
(defun KG-RepHealInsName (e)
  (KG-AsString (cdr (assoc 2 (KG-Safe '(lambda () (entget e)) nil))))
)

;; База паспорта вставки (имя определения из ссылки 340) или nil.
(defun KG-RepHealChain (ins / d sec sub dat rec r)
  (setq d (KG-Safe '(lambda () (cdr (assoc 360 (entget ins)))) nil))
  (if (null d)
    nil
    (progn
      (setq sec (KG-Safe '(lambda () (dictsearch d "AcDbBlockRepresentation")) nil))
      (setq sub (if sec (cdr (assoc -1 sec)) nil))
      (if (null sub)
        nil
        (progn
          (setq dat (KG-Safe '(lambda () (cdr (assoc -1 (dictsearch sub "AcDbRepData")))) nil))
          (if (null dat)
            nil
            (progn
              (setq rec (KG-Safe '(lambda () (cdr (assoc 340 (entget dat)))) nil))
              (if (null rec)
                nil
                (progn
                  (setq r (KG-Safe '(lambda () (cdr (assoc 2 (entget rec)))) nil))
                  (if r (KG-AsString r) nil)
                )
              )
            )
          )
        )
      )
    )
  )
)

;; Запись BLOCK_RECORD определения по имени (для ссылки 340) или nil.
(defun KG-RepHealRecOf (nm)
  (KG-Safe '(lambda () (cdr (assoc 330 (entget (tblobjname "BLOCK" nm))))) nil)
)

;; Записать недостающий паспорт вставке ins с базой basename. Здоровый
;; паспорт не трогается. Возврат T/nil.
(defun KG-RepHealWrite (ins basename / d sub dat rec)
  (setq d (KG-Safe '(lambda () (cdr (assoc 360 (entget ins)))) nil))
  (if (null d)
    nil
    (if (KG-Safe '(lambda () (dictsearch d "AcDbBlockRepresentation")) nil)
      nil
      (progn
        (setq rec (KG-RepHealRecOf basename))
        (if (null rec)
          nil
          (progn
            (setq sub (KG-Safe '(lambda ()
                                  (entmakex (list (cons 0 "DICTIONARY")
                                                  (cons 100 "AcDbDictionary")
                                                  (cons 280 1)
                                                  (cons 281 1)))) nil))
            (setq dat (KG-Safe '(lambda ()
                                  (entmakex (list (cons 0 "ACDB_BLOCKREPRESENTATION_DATA")
                                                  (cons 100 "AcDbBlockRepresentationData")
                                                  (cons 70 1)
                                                  (cons 340 rec)))) nil))
            (if (and sub dat)
              (progn
                (KG-Safe '(lambda () (dictadd sub "AcDbRepData" dat)) nil)
                (KG-Safe '(lambda () (dictadd d "AcDbBlockRepresentation" sub)) nil)
                T
              )
              nil
            )
          )
        )
      )
    )
  )
)

;; Карта «представление -> имя базы» по здоровым паспортам определений и
;; пространств. Пары добавляются по первой встрече.
(defun KG-RepHealMap (defs / m rn b ss i e d p)
  (setq m nil)
  (foreach d defs
    (foreach p (cdr d)
      (setq rn (KG-RepHealInsName (cdr p)))
      (if (KG-RepHealIsRep rn)
        (progn
          (setq b (KG-RepHealChain (cdr p)))
          (if (and b (/= b "") (not (KG-AssocCI rn m)))
            (setq m (cons (cons rn b) m))
          )
        )
      )
    )
  )
  (setq ss (KG-Safe '(lambda () (ssget "_X" (list (cons 0 "INSERT")))) nil))
  (if ss
    (progn
      (setq i 0)
      (while (< i (KG-AsNum (KG-Safe '(lambda () (sslength ss)) 0) 0))
        (setq e (KG-Safe '(lambda () (ssname ss i)) nil))
        (setq rn (if e (KG-RepHealInsName e) nil))
        (if (KG-RepHealIsRep rn)
          (progn
            (setq b (KG-RepHealChain e))
            (if (and b (/= b "") (not (KG-AssocCI rn m)))
              (setq m (cons (cons rn b) m))
            )
          )
        )
        (setq i (1+ i))
      )
    )
  )
  m
)

;; Основной проход лечения. Возврат -- список (вылечено, осталось).
(defun KG-RepHealRun ( / defs norms repbases d nm ents mynorm i p ed rn base
                       src twininfo cand pr nm2 p2 ed2 r2 b2 pass again total
                       cnt nleft used mykey)
  (setq defs nil norms nil)
  (setq d (KG-Safe '(lambda () (tblnext "BLOCK" T)) nil))
  (while d
    (setq nm (KG-AsString (cdr (assoc 2 d))))
    (setq ents (KG-RepHealEnts nm))
    (setq defs (cons (cons nm ents) defs))
    (setq norms (cons (cons nm (mapcar '(lambda (x) (KG-RepHealNormTok (car x))) ents)) norms))
    (setq d (KG-Safe '(lambda () (tblnext "BLOCK")) nil))
  )
  (setq pass 0 again T total 0 nleft 0 used nil)
  (while (and again (< pass 4))
    (setq pass (1+ pass) cnt 0 nleft 0)
    (setq repbases (KG-RepHealMap defs))
    (foreach d defs
      (setq nm (car d) ents (cdr d) mynorm (KG-CdrCI nm norms) i 0)
      (foreach p ents
        (setq ed (KG-Safe '(lambda () (entget (cdr p))) nil))
        (if (and ed
                 (KG-StrEq (KG-AsString (cdr (assoc 0 ed))) "INSERT")
                 (KG-RepHealIsRep (KG-AsString (cdr (assoc 2 ed)))))
          (progn
            (setq rn (KG-AsString (cdr (assoc 2 ed))))
            (if (null (KG-RepHealChain (cdr p)))
              (progn
                (setq base (cdr (KG-AssocCI rn repbases)))
                (setq src "карта" twininfo "")
                (if (null base)
                  (progn
                    (setq cand nil src "близнец")
                    (foreach pr norms
                      (setq nm2 (car pr))
                      (if (and (not (KG-StrEq nm2 nm))
                               (equal (cdr pr) mynorm))
                        (progn
                          (setq p2 (nth i (KG-CdrCI nm2 defs)))
                          (if p2
                            (progn
                              (setq ed2 (KG-Safe '(lambda () (entget (cdr p2))) nil))
                              (if (and ed2
                                       (KG-StrEq (KG-AsString (cdr (assoc 0 ed2))) "INSERT")
                                       (KG-RepHealIsRep (KG-AsString (cdr (assoc 2 ed2)))))
                                (progn
                                  (setq r2 (KG-AsString (cdr (assoc 2 ed2))))
                                  (setq b2 (KG-RepHealChain (cdr p2)))
                                  (if (and b2 (/= b2 "")
                                           (KG-CdrCI rn defs) (KG-CdrCI r2 defs)
                                           (equal (KG-RepHealSorted (KG-CdrCI rn defs))
                                                  (KG-RepHealSorted (KG-CdrCI r2 defs))))
                                    (progn
                                      (if (not (KG-StrInterCI (list b2) cand))
                                        (setq cand (cons b2 cand))
                                      )
                                      (setq twininfo (strcat " через " nm2 "/" r2))
                                    )
                                  )
                                )
                              )
                            )
                          )
                        )
                      )
                    )
                    (if (= (length cand) 1) (setq base (car cand)))
                    (if (> (length cand) 1)
                      (KG-TraceDetail
                        (strcat "лечение: " nm "/" (KG-AsString (cdr (assoc 5 ed)))
                                " -> " rn ": неоднозначно: " (vl-princ-to-string cand))
                      )
                    )
                  )
                )
                (if base
                  (if (KG-RepHealWrite (cdr p) base)
                    (progn
                      (setq cnt (1+ cnt))
                      (setq used (cons (strcat rn " => \"" base "\"") used))
                      (KG-TraceDetail
                        (strcat "лечение: " nm "/" (KG-AsString (cdr (assoc 5 ed)))
                                " -> " rn " => \"" base "\" (" src twininfo ")"))
                    )
                    (progn
                      (setq nleft (1+ nleft))
                      (KG-TraceDetail
                        (strcat "лечение: " nm "/" (KG-AsString (cdr (assoc 5 ed)))
                                " -> " rn ": запись не удалась"))
                    )
                  )
                  (progn
                    (setq nleft (1+ nleft))
                    (KG-TraceDetail
                      (strcat "лечение: " nm "/" (KG-AsString (cdr (assoc 5 ed)))
                              " -> " rn ": база не найдена"))
                  )
                )
              )
            )
          )
        )
        (setq i (1+ i))
      )
    )
    (setq total (+ total cnt) again (> cnt 0))
  )
  (setq used (KG-Unique used))
  (KG-Say (strcat "Вылечено вставок: " (itoa total)
                  (if (> pass 1) (strcat " (проходов: " (itoa pass) ")") "")))
  (if used
    (progn
      (KG-Say "Вылеченные паспорта (представление => база):")
      (foreach mykey (reverse used) (KG-Say (strcat "  " mykey)))
    )
  )
  (if (= total 0) (KG-Say "Повреждённых паспортов не найдено."))
  (if (> nleft 0)
    (KG-Say (strcat "Осталось повреждённых: " (itoa nleft)
                    " (подробности: (setq KG-TRACE-DETAIL t))"))
  )
  (list total nleft)
)


;;;--- Сиротские анонимные представления ------------------------------------
;;;
;;; PURGE их не снимает: на реальном чертеже три прохода PURGE унесли 110
;;; определений, а 180 сиротских *U остались. Вместе с ними остались шесть
;;; старых вложенных определений «...~до»: PURGE внутрь анонимного
;;; представления не заглядывает, поэтому «kps 920~до» для него выглядит
;;; использованным. Стираем *U сами (ENTD по записи таблицы блоков) --
;;; вставок у сироты нет по построению, стирать нечего, -- и следующий
;;; PURGE уносит освободившиеся определения.

;; Имя определения, на которое указывает вставка. Пустая строка, если
;; ename не читается.
(defun KG_DefNameOfEnt (e / ed)
  (setq ed (KG-Safe '(lambda () (entget e)) nil))
  (if ed (KG-AsString (cdr (assoc 2 ed))) "")
)

;; Имена вставок внутри определения (вложенные блоки, в том числе
;; вложенные анонимные представления). Только entget: COM-обход
;; содержимого определений на реальном чертеже дал 0xC0000005.
(defun KG_DefEntNames (defname / e ed out kg-t0)
  ;; 71.6: обход содержимого определения -- общая дорогая часть и
  ;; перепривязки ссылок, и поиска держателей ссылок. Суб-замер называет
  ;; её вклад отдельно.
  (setq kg-t0 (KG-SubT0))
  (setq out nil)
  (setq e (KG-Safe '(lambda () (KG-DefEnt defname)) nil))
  (if e
    (while (and (setq e (KG-Safe '(lambda () (entnext e)) nil))
                (setq ed (KG-Safe '(lambda () (entget e)) nil))
                (/= (KG-AsString (cdr (assoc 0 ed))) "ENDBLK"))
      (if (KG-StrEq (KG-AsString (cdr (assoc 0 ed))) "INSERT")
        ;; ed уже прочитан выше: второй entget ради группы 2 стоил
        ;; половины обхода на крупных определениях.
        (setq out (cons (KG-AsString (cdr (assoc 2 ed))) out))
      )
    )
  )
  (KG-SubT1 "обход содержимого определения (KG_DefEntNames)" kg-t0)
  (reverse out)
)

;; Карта «сиротское *U -> что внутри». Нужна для отчёта: по ней видно,
;; какие именно определения держат сироты и что освободится.
(defun KG-OrphanContents (orph / out nm inner)
  (setq out nil)
  (foreach nm orph
    (setq inner (KG-Safe '(lambda () (KG_DefEntNames nm)) nil))
    (setq out (cons (cons nm (KG-Unique inner)) out))
  )
  out
)

;;;--- Перепривязка ссылок на переименованные определения --------------------
;;
;; Задача: вносимый мастер-блок приносит более свежие версии блоков. Одноимённое
;; определение чертежа должно получить новое содержимое ПО ВСЕМУ чертежу -- не
;; только там, где его вставляют в модель, но и внутри чужих определений.
;;
;; Как это устроено. До вставки из буфера имя освобождается: определение
;; переименовывается в «~имя», и AutoCAD уводит за ним все свои
;; ссылки. Из буфера приходит определение под прежним именем -- с новым
;; содержимым. Дальше ссылки надо вернуть на прежнее имя: тогда и чужие
;; определения, и анонимные представления начинают указывать на свежую версию,
;; а служебное имя «~имя» остаётся без ссылок и его снимает PURGE.
;;
;; Без этого шага на реальном чертеже после прогона осталось 31 определение
;; «имя~до» с нулём вставок, и PURGE их не взял: значит, ссылки на них ещё были.

;; Есть ли внутри определения вставка указанного определения.
(defun KG-DefRefersTo (defname tgt / out)
  (setq out nil)
  (foreach nm (KG-Safe '(lambda () (KG_DefEntNames defname)) nil)
    (if (KG-StrEq nm tgt) (setq out t))
  )
  (if out t nil)
)

;; Кто держит служебные определения прошлой интеграции («~ИМЯ», у прежних
;; сборок «ИМЯ~до»). Нужна отчёту: «осталось N» без имён держателей не
;; отличить от «ссылок нет, PURGE их просто не берёт». Держатели берутся из
;; готовой карты ссылок, поэтому отдельного обхода таблицы блоков здесь нет.
(defun KG-DoHolderLines (holders names / out nm hh h x lines shown)
  (setq out nil)
  (setq lines 0)
  (foreach nm names
    (if (and (< lines 8) (KG-IsTempDefName nm))
      (progn
        (setq hh (KG-CdrCI (KG-AsString nm) (KG-Unmark holders)))
        (if hh
          (progn
            ;; Три держателя на определение и восемь определений: на реальном
            ;; чертеже их десятки, а строка нужна как диагноз, а не как дамп.
            (setq shown "")
            (setq h 0)
            (foreach x hh
              (if (< h 3)
                (progn
                  (setq shown (strcat shown (if (= shown "") "" ", ")
                                      (KG-AsString x)))
                  (setq h (1+ h))
                )
              )
            )
            (setq out (cons (strcat "  \"" nm "\" держат: " shown) out))
            (setq lines (1+ lines))
          )
        )
      )
    )
  )
  (reverse out)
)

;; Какие определения вставляют данное определение. Обход идёт по ВСЕМ именам
;; таблицы, включая анонимные представления: именно там ссылки на «~ИМЯ»
;; и остаются.
;;
;; 71.7. Прежний обход заново сканировал содержимое всех определений на
;; каждый вопрос: у пар перепривязки имена разные, кэш «по имени-ключу» не
;; помогал, и на одном семействе это стоило 56.8 с (прогон 71.6), а на трёх
;; семействах -- 247 с. Теперь ответ берётся из общей карты шага
;; (KG-RefMapBuild), а правки карты точечные (KG-RefMapRewire) -- читается
;; содержимое одного определения. Прежний обход оставлен эталоном для T30.

;; Ведро карты: положить (kg-on) или убрать (не kg-on) определение kg-who
;; в ведре kg-key. Новые держатели добавляются в КОНЕЦ: порядок совпадает
;; с порядком KG_EXAllDefNames -- как у прежнего обхода.
(defun KG-RefMapSet (kg-key kg-who kg-on kg-map / kg-p kg-val kg-hold kg-e)
  ;; 72. Точный поиск ведра -- первым: ключи приходят из чертежа
  ;; (возвращаются обоими каналами: KG-RMCdr), и совпадение написания --
  ;; правило, а не исключение. KG-AssocCI со strcase на каждую запись
  ;; остался запасным путём для запросов «в другом регистре».
  (setq kg-p (assoc (KG-AsString kg-key) kg-map))
  (if (not kg-p) (setq kg-p (KG-AssocCI kg-key kg-map)))
  (setq kg-val (if kg-p (cdr kg-p) nil))
  (if kg-on
    (if (not (member kg-who kg-val))
      (setq kg-val (append kg-val (list kg-who)))
    )
    (progn
      (setq kg-val nil)
      (foreach kg-e (if kg-p (cdr kg-p) nil)
        (if (not (KG-StrEq kg-e kg-who))
          (setq kg-val (cons kg-e kg-val))
        )
      )
      (setq kg-val (reverse kg-val))
    )
  )
  ;; Ведро ищется без учёта регистра, как и сравнение имён в KG-DefRefersTo:
  ;; «KPS 741» и «kps 741» -- одно написание, попадать они обязаны в одно
  ;; ведро. Ключ существующего ведра не переписывается: он взят из чертежа.
  (setq kg-hold (if kg-p (car kg-p) (KG-AsString kg-key)))
  ;; 72. Точечная замена ведра: subst трогает только найденную пару, и
  ;; весь список заново не пересобирается (это и было основное время).
  (if kg-p
    (subst (cons kg-hold kg-val) kg-p kg-map)
    (cons (cons kg-hold kg-val) kg-map)
  )
)

;; 72. Быстрый поиск в карте «кто вставляет» (KG-EXRefHolders, KG-RefMapBuild).
;; Точное сравнение -- основное, без учёта регистра -- запасное. Возвращается
;; сам cdr, как у KG-CdrCI.
(defun KG-RMCdr (key alst / p)
  (setq p (assoc (KG-AsString key) alst))
  (if p (cdr p) (KG-CdrCI key alst))
)

;; 72. Быстрая запись ведра в ту же карту: точное сравнение, subst вместо
;; полной пересборки, запись на месте (длина карты не растёт).
(defun KG-RMSet (key val alst / p)
  (setq p (assoc (KG-AsString key) alst))
  (if (not p) (setq p (KG-AssocCI key alst)))
  (if p
    (subst (cons (car p) val) p alst)
    (cons (cons (KG-AsString key) val) alst)
  )
)

(if (not (boundp 'KG-RAW-NESTED)) (setq KG-RAW-NESTED nil))

;; Снимок содержимого всех определений: имя -> фактические имена вставок
;; (группа 2), в порядке содержимого. Только DXF, без COM: карте ссылок
;; нужны именно фактические имена. Строится один раз перед шагом
;; перепривязки ссылок; правки определений в этом шаге сбрасывают
;; затронутые записи (KG-RawNestedDrop).
(defun KG-RawNestedBuild ( / out d nm e ed lst)
  (setq out nil)
  (setq d (KG-Safe '(lambda () (tblnext "BLOCK" t)) nil))
  (while d
    (setq nm (KG-AsString (cdr (assoc 2 d))))
    (setq lst nil)
    (setq e (cdr (assoc -2 d)))
    (while e
      (setq ed (KG-Safe '(lambda () (entget e)) nil))
      (if (and ed (/= (KG-AsString (cdr (assoc 0 ed))) "ENDBLK"))
        (progn
          (if (KG-StrEq (KG-AsString (cdr (assoc 0 ed))) "INSERT")
            (setq lst (cons (KG-AsString (cdr (assoc 2 ed))) lst))
          )
          (setq e (KG-Safe '(lambda () (entnext e)) nil))
        )
        (setq e nil)
      )
    )
    (if (/= nm "")
      (setq out (cons (cons nm (reverse lst)) out))
    )
    (setq d (KG-Safe '(lambda () (tblnext "BLOCK")) nil))
  )
  (reverse out)
)

;; Сбросить запись снимка для одного определения (его содержимое изменили).
(defun KG-RawNestedDrop (defname / out)
  (setq out nil)
  (foreach p KG-RAW-NESTED
    (if (not (KG-StrEq (KG-AsString (car p)) (KG-AsString defname)))
      (setq out (cons p out))
    )
  )
  (setq KG-RAW-NESTED out)
)

;; Имя определения, внутри которого лежит объект (группа 330).
;; Группа 330 приходит то handle'ом, то ename'ом -- разбираются оба вида.
(defun KG-DefOwnerName (h / e oh oe)
  (setq e (KG-Safe '(lambda () (handent (KG-AsString h))) nil))
  (setq oh (if e (KG-Safe '(lambda () (cdr (assoc 330 (entget e)))) nil) nil))
  (cond
    ((null oh) nil)
    ((= (type oh) (type "")) (KG-RecordNameOf oh))
    (t
     (setq oe (KG-Safe '(lambda () (entget oh)) nil))
     (if oe (KG-AsString (cdr (assoc 2 oe))) nil))
  )
)

;; Имена вставок определения для карты ссылок: если определение уже
;; прочитано снимком KG-RAW-NESTED, берём оттуда -- без повторного
;; обхода содержимого; иначе читаем как раньше.
(defun KG-RefMapDefNames (defname / p)
  (setq p (assoc (KG-AsString defname) KG-RAW-NESTED))
  (if p (cdr p) (KG_DefEntNames defname))
)

;; Построение карты одним проходом по всем определениям чертежа.
(defun KG-RefMapBuild ( / kg-t0 kg-nm kg-x kg-val)
  (setq kg-t0 (KG-SubT0))
  (setq KG-REFREV nil)
  (foreach kg-nm (KG-Safe '(lambda () (KG_EXAllDefNames)) nil)
    (if (/= (KG-AsString kg-nm) "")
      (foreach kg-x (KG-Safe '(lambda () (KG-RefMapDefNames kg-nm)) nil)
        ;; Вставка определения самого в себя -- петля, держателем оно не
        ;; становится. То же исключение делает и KG-DefRefersTo.
        (if (not (KG-StrEq kg-nm kg-x))
          ;; 72. Ведро берётся точным поиском, держатель добавляется в
          ;; конец (порядок KG_EXAllDefNames) -- как у прежнего обхода.
          (progn
            (setq kg-val (KG-RMCdr kg-x KG-REFREV))
            (if (not (member (KG-AsString kg-nm) kg-val))
              (setq KG-REFREV
                (KG-RMSet kg-x (append kg-val (list (KG-AsString kg-nm)))
                          KG-REFREV))
            )
          )
        )
      )
    )
  )
  (setq KG-REFREV-ON t)
  (KG-SubT1 "перепривязка: карта ссылок (построение)" kg-t0)
  KG-REFREV
)

;; Карта для работы: не построена -- строится. Сбрасывается KG-RefMapDrop.
(defun KG-RefMapEnsure ()
  (if (not KG-REFREV-ON) (KG-RefMapBuild))
  KG-REFREV
)

(defun KG-RefMapDrop ()
  ;; Если карта была построена и её пришлось сбросить (правку не удалось
  ;; учесть точечно), снимок содержимого определений уже устарел: любая
  ;; пересборка обязана читать чертёж заново. Сброс в начале шага (карты
  ;; ещё нет) снимок не трогает -- он нужен этому шагу.
  (if KG-REFREV-ON (setq KG-RAW-NESTED nil))
  (setq KG-REFREV nil)
  (setq KG-REFREV-ON nil)
  nil
)

;; Точечная правка карты после перепривязки ссылок в определении holder.
;; Содержимое holder читается заново ОДИН раз, и состав вёдер берётся из
;; фактического содержимого: entmod мог исправить не все вставки, и по
;; счётчику не видно, осталась ли ссылка.
;; Отдаёт t, когда карта в порядке; nil -- когда содержимое не прочиталось:
;; тогда KG-RewireOnePair сбрасывает карту целиком -- полная пересборка
;; дешевле устаревшего ответа.
(defun KG-RefMapRewire (holder oldname newname / kg-t0 kg-lst kg-ok kg-old kg-new kg-x)
  (if (not KG-REFREV-ON)
    t
    (progn
      (setq kg-t0 (KG-SubT0))
      (setq kg-lst (KG-Safe '(lambda () (KG_DefEntNames holder)) "*FAIL*"))
      (setq kg-ok (not (= (type kg-lst) (type ""))))
      (if kg-ok
        (progn
          (setq kg-old nil)
          (setq kg-new nil)
          (foreach kg-x kg-lst
            (if (KG-StrEq kg-x oldname) (setq kg-old t))
            (if (KG-StrEq kg-x newname) (setq kg-new t))
          )
          ;; Из ведра старого имени держатель уходит, только когда ссылки в
          ;; нём больше нет; в ведро нового -- приходит, когда ссылка есть.
          ;; Себя держателем не делаем: KG-DefRefersTo самого определения
          ;; не считает, и ведро обязано отвечать так же.
          (if (not (KG-StrEq holder oldname))
            (setq KG-REFREV (KG-RefMapSet oldname holder kg-old KG-REFREV))
          )
          (if (not (KG-StrEq holder newname))
            (setq KG-REFREV (KG-RefMapSet newname holder kg-new KG-REFREV))
          )
        )
      )
      (KG-SubT1 "перепривязка: правка карты" kg-t0)
      (if kg-ok t nil)
    )
  )
)

;; 71.7. Держатели берутся из карты шага: ответ на любое имя -- поиск в
;; списке, а не обход чертежа.
(defun KG-DefRefHolders (tgt / pr)
  (KG-RefMapEnsure)
  ;; 72. Сначала точное написание (ведра собраны из имён чертежа), и
  ;; лишь затем поиск без учёта регистра.
  (setq pr (assoc (KG-AsString tgt) KG-REFREV))
  (if (not pr) (setq pr (KG-AssocCI (KG-AsString tgt) KG-REFREV)))
  (if pr (cdr pr) nil)
)

;; Прежний обход -- эталон для T30: заново сканирует содержимое ВСЕХ
;; определений на каждый запрос. Оставлен в файле намеренно -- как
;; KG-SourceOfNested для карты вложений.
(defun KG-RefHoldersLegacy (tgt / out nm)
  (setq out nil)
  (foreach nm (KG-Safe '(lambda () (KG_EXAllDefNames)) nil)
    ;; Исключается только само старое определение: вставка блока самого в
    ;; себя была бы петлёй. Новое определение держателем быть МОЖЕТ --
    ;; именно там лежит ссылка, которая возвращается на следующем проходе:
    ;; «Гайка» из буфера вставляет «~Шайба», а «Шайба» становится
    ;; прежней только вместе с «Гайкой».
    (if (and nm (/= (KG-AsString nm) "")
             (not (KG-StrEq nm (KG-AsString tgt))))
      (if (KG-Safe '(lambda () (KG-DefRefersTo nm tgt)) nil)
        (setq out (cons nm out))
      )
    )
  )
  (KG-Unique (reverse out))
)

;; Как будет называться определение после перепривязки. Ищется в списке
;; пар текущего прохода (KG-REWPAIRS); без пары имя остаётся как есть.
;; К моменту, когда чертёж откроют, служебные ссылки уже возвращены на
;; прежние имена, поэтому проверка замыкания обязана смотреть на граф ПОСЛЕ
;; перепривязки, а не на текущий.
;;
;; Служебная отметка здесь НАМЕРЕННО не снимается по написанию: имена
;; перепривязываются по списку пар (KG-REWPAIRS), а обрезание по «~» или
;; «до» исказило бы имя чужого определения.
(defun KG-RewResolve (nm / k pr)
  (setq k (KG-AsString nm))
  (foreach pr KG-REWPAIRS
    (if (KG-StrEq (nth 1 pr) k) (setq k (KG-AsString (nth 0 pr))))
  )
  k
)

;; Замкнётся ли определение, если внутри holder вернуть ссылку на oldname.
;; Проверяется достижимость holder из newname по ссылкам вложенных блоков:
;; если holder достижим, ссылка «holder -> newname» замыкает цепочку.
;;
;; Обход в ширину, а не по первой вложенной ссылке: на реальном чертеже у
;; определения их десятки, и нужная почти никогда не первая. Прежняя версия
;; брала только первую -- на стенде она отвечала «не замкнётся» там, где
;; замыкание было, и шаг переписывал группу 2 у определения, которое после
;; этого ссылалось само на себя.
;;
;; Имена приводятся к виду после перепривязки (KG-RewResolve): иначе обход
;; упирался в островок старых определений, которые ссылаются друг на друга,
;; и до holder не доходил никогда.
;; Предел -- 400 определений: дальше это уже не проверка, а обход чертежа.
(defun KG-WouldCycle (holder oldname newname / front seen add cur key res
                                             inner x hit n)
  (setq hit nil)
  (setq res (KG-RewResolve holder))
  (setq front (list (KG-AsString newname)))
  (setq seen nil)
  (setq n 0)
  (while (and (not hit) front (< n 400))
    (setq cur (car front))
    (setq front (cdr front))
    (setq key (KG-RewResolve cur))
    (if (KG-StrEq key res)
      (setq hit t)
      (if (KG-StrInterCI (list key) seen)
        nil
        (progn
          (setq seen (cons key seen))
          (setq n (1+ n))
          (setq inner (KG-Safe '(lambda () (KG_DefEntNames cur)) nil))
          ;; Найденное собирается в ОТДЕЛЬНЫЙ список и добавляется к очереди
          ;; после обхода. Дописывать в саму очередь внутри foreach нельзя:
          ;; обход идёт по тому списку, который был передан, и добавленные
          ;; элементы теряются. Именно так первая версия проверки отвечала
          ;; «не замкнётся» там, где замыкание было.
          (setq add nil)
          (foreach x inner
            (if (and x
                     (not (KG-StrInterCI (list (KG-RewResolve x)) seen))
                     (not (KG-StrInterCI (list (KG-RewResolve x)) add)))
              (setq add (cons x add))
            )
          )
          (setq front (append front (reverse add)))
        )
      )
    )
  )
  (if hit t nil)
)

;; Вернуть ссылку внутри определения holder с oldname на newname.
;; Отдаёт число исправленных вставок.
(defun KG-RewireDefRefs (holder oldname newname / e ed n hit x newed)
  (setq n 0)
  (setq e (KG-Safe '(lambda () (KG-DefEnt holder)) nil))
  (if e
    (while (and (setq e (KG-Safe '(lambda () (entnext e)) nil))
                (setq ed (KG-Safe '(lambda () (entget e)) nil))
                (/= (KG-AsString (cdr (assoc 0 ed))) "ENDBLK"))
      (if (KG-StrEq (KG-AsString (cdr (assoc 0 ed))) "INSERT")
        (if (KG-StrEq (KG-AsString (cdr (assoc 2 ed))) oldname)
          (progn
            ;; Правится группа 2 -- имя вставляемого определения. Прочие
            ;; группы передаются обратно без изменений: entmod переписывает
            ;; сущность целиком. Список пересобирается в лоб, а не через
            ;; KG-SetAssoc: тот сравнивает ключи через KG-AsString, и число 2
            ;; у него не равно строке "2", которой assoc ищет группу в
            ;; AutoCAD. Ключ записывается числом, каким он и пришёл.
            (setq newed nil)
            (foreach x ed
              ;; Код группы сравнивается через KG-StrEq, а не через «=»:
              ;; у списка сущности могут встретиться записи, где в car не
              ;; число, и «=» на смешанных типах в AutoCAD поднимает ошибку.
              (if (KG-StrEq (car x) 2)
                (setq newed (cons (cons 2 (KG-AsString newname)) newed))
                (setq newed (cons x newed))
              )
            )
            (setq newed (reverse newed))
            (setq hit (KG-Safe '(lambda () (entmod newed)) nil))
            (if hit
              (progn
                (setq n (1+ n))
                (KG-Safe '(lambda () (entupd e)) nil)
              )
            )
          )
        )
      )
    )
  )
  n
)

;; Одно переименование: вернуть все найденные ссылки на прежнее имя.
(defun KG-RewireOnePair (oldname newname / holders h n nh skipped kg-t0 kg-cyc)
  (setq n 0)
  (setq skipped 0)
  (if (and oldname newname
           (/= (KG-AsString oldname) "")
           (not (KG-StrEq oldname newname)))
    (progn
      (KG-TraceDetail (strcat "перепривязка ссылок \"" oldname "\""))
      (setq kg-t0 (KG-SubT0))
      (setq holders (KG-Safe '(lambda () (KG-DefRefHolders oldname)) nil))
      (KG-SubT1 "перепривязка: держатели ссылки" kg-t0)
      (foreach h holders
        ;; Определения, которые входят в состав нового, не трогаются: ссылка
        ;; «новое -> старое» внутри цепочки замкнула бы определение.
        (setq kg-t0 (KG-SubT0))
        (setq kg-cyc (KG-Safe '(lambda () (KG-WouldCycle h oldname newname)) nil))
        (KG-SubT1 "перепривязка: проверка замыкания" kg-t0)
        (if kg-cyc
          (progn
            (setq skipped (1+ skipped))
            (if (not (KG-StrInterCI (list oldname) KG-REWSKIP))
              (setq KG-REWSKIP (cons oldname KG-REWSKIP))
            )
          )
          (progn
            (setq kg-t0 (KG-SubT0))
            (setq nh (KG-AsNum (KG-Safe
                           '(lambda () (KG-RewireDefRefs h oldname newname)) 0) 0))
            (setq n (+ n nh))
            (KG-SubT1 "перепривязка: правка ссылок" kg-t0)
            ;; 71.7: карта держателей правится точечно -- заново читается
            ;; содержимое ОДНОГО определения, а не всего чертежа. Если
            ;; поправить не удалось, карта сбрасывается целиком.
            (if (> nh 0)
              (if (not (KG-Safe
                         '(lambda () (KG-RefMapRewire h oldname newname)) nil))
                (KG-RefMapDrop)
              )
            )
          )
        )
      )
      (if (> skipped 0)
        (princ (strcat "\nВНИМАНИЕ: вставка \"" oldname "\" внутри \""
                       newname "\" оставлена как есть -- иначе определение "
                       "замкнулось бы само на себя."))
      )
    )
  )
  n
)

;; Перепривязать одну пару из списка. Отдельная функция, а не лямбда внутри
;; KG-Safe в теле цикла: лямбда, цитирующая локальную переменную цикла,
;; подставляется ненадёжно -- на стенде такой вызов молча отдавал запасное
;; значение, и шаг не перепривязывал ничего, не сообщая об отказе.
;;
;; Настоящая причина -- найдена пробой на живом AutoCAD (сборка 71.1).
;; У лямбды подстановка ДИНАМИЧЕСКАЯ: свободная переменная берётся из
;; ближайшей рамки. Между лямбдой и телом этой функции стоит рамка KG-Safe,
;; а в ней есть СВОЯ переменная r -- результат перехвата, в момент вызова
;; ещё пустая. Лямбда брала именно её: имена приходили пустыми,
;; KG-RewireOnePair сразу отвечала «0», и шаг молча не перепривязывал
;; ничего. Числа пробы: KG-RewireOnePair напрямую -- 1, он же под обёрткой с
;; готовыми строками -- 1, а через эту обёртку -- 0. Теперь аргумент
;; называется pr, а у KG-Safe имена убраны за приставку kg-, чтобы
;; свободные имена лямбд ничего не задевали.
(defun KG-RewirePairOf (pr)
  ;; Порядок аргументов: сперва служебное имя «~ИМЯ», затем прежнее. Пара в
  ;; renames лежит наоборот -- (прежнее служебное), и перестановка здесь
  ;; обязательна: первая версия передавала их как есть, держатели искались
  ;; по прежнему имени, не находились, и шаг молча не перепривязывал ничего.
  (KG-Safe '(lambda () (KG-RewireOnePair (nth 1 pr) (nth 0 pr))) 0)
)

;; Шаг 8б. Вернуть ссылки на прежние имена по всем парам переименования.
;; Проходит пары по кругу: за один проход часть ссылок ещё указывает на
;; служебное имя, которое само станет прежним только на следующем. Круг
;; прерывается, когда за проход не исправлено ни одной вставки, -- иначе две
;; пары, ссылающиеся друг на друга, крутились бы вечно.
(defun KG-Step_RewireDefs (renames / todo r done total n pairs guard stuck kg-t0)
  ;; 71.7: карта держателей -- одна на запуск шага. Между запусками чертёж
  ;; меняют другие шаги (снятие старых определений, очистка), поэтому сброс
  ;; в начале и конце обязателен: внутри шага карта верна всегда -- каждая
  ;; правка ссылок правит её точечно (KG-RefMapRewire).
  (KG-RefMapDrop)
  (setq KG-REWSKIP nil)
  (setq total 0)
  (setq todo nil)
  (foreach r renames
    (if (and (nth 0 r) (nth 1 r)
             (/= (KG-AsString (nth 0 r)) "")
             (not (KG-StrEq (nth 0 r) (nth 1 r))))
      (setq todo (cons (list (nth 0 r) (nth 1 r)) todo))
    )
  )
  (setq todo (reverse todo))
  (setq guard 0)
  (while (and todo (< guard 12))
    (setq pairs todo)
    (setq KG-REWPAIRS todo)
    (setq todo nil)
    (setq done 0)
    (foreach r pairs
      (setq kg-t0 (KG-SubT0))
      (setq n (KG-AsNum (KG-RewirePairOf r) 0))
      (KG-SubT1 "перепривязка: пара (всего)" kg-t0)
      (setq done (+ done n))
      (if (< n 1) (setq todo (cons r todo)))
    )
    (setq todo (reverse todo))
    (setq total (+ total done))
    ;; 71.9. Ранний выход, обещанный комментарием в начале шага: круг
    ;; прерывается, когда за проход не исправлено ни одной вставки. Прежде
    ;; условием выхода были только «12 проходов»: на живом прогоне 71.8
    ;; из 2737 пар больше 2000 приходились на такие пустые повторы -- пары,
    ;; которым возвращать нечего, прокручивались все 12 раз, и каждый
    ;; повтор заново искал держателей.
    (setq stuck (length todo))
    (if (or (null todo) (< done 1)) (setq todo nil))
    (setq guard (1+ guard))
  )
  ;; Остаток в списке -- это пары, которые за 12 проходов так ничего и не
  ;; исправили. Чаще всего это не отказ: переименование через vla-put-Name
  ;; уже уводит за именем ссылки AutoCAD, и возвращать нечего. Поэтому
  ;; предупреждение печатается только тогда, когда есть пропуски из-за риска
  ;; зациклить определение -- про них пользователь должен знать. В прогоне
  ;; на 43 парах здесь печатался список из 43 имён при нуле пропусков, и
  ;; читался он как авария там, где её не было.
  (if KG-REWSKIP
    (princ (strcat "\nОставлены как есть, иначе определение замкнулось бы: "
                   (KG-JoinNames (reverse KG-REWSKIP)))))
  (if (> (KG-AsNum stuck 0) 0)
    (KG-TraceDetail (strcat "пар без найденных ссылок: "
                            (KG-NumStr stuck))))
  ;; Карта нужна только внутри шага: дальше чертёж меняют другие шаги.
  (KG-RefMapDrop)
  (setq KG-REWPAIRS nil)
  (KG-Mark (strcat "перепривязано ссылок на прежние имена: "
                   (KG-NumStr total)))
  total
)

;;;--- Видимость вложенных блоков внутри определений -------------------------
;;
;; Определение без итерации в имени («Стойка КП50», «Закладная в полость
;; стойки») подменяется целиком: старое переименовывается в «~имя», из
;; буфера приходит новое под прежним именем. Содержимое при этом обновляется
;; верно, а вот состояния видимости вложенных блоков сбрасываются в значения
;; по умолчанию новой версии -- прогон это подтвердил: блоки с итерацией
;; видимость сохраняют (у них состояния переносятся по экземплярам), а блоки
;; без итерации теряют.
;;
;; Поэтому состояния читаются ДО освобождения имён и записываются обратно
;; после перепривязки.

;; Состояния видимости вложенных вставок одного определения. Определения без
;; вложенных вставок в список не попадают: на крупном чертеже их большинство,
;; а COM-чтение свойств -- самая дорогая часть обхода.
;;
;; Второй элемент результата -- сколько вложенных вставок осталось БЕЗ
;; состояния: у них либо нет параметра видимости, либо имя не прочиталось.
;; Без этого числа «снято 27 состояний» и «в определении 9 вложенных вставок,
;; состояний прочитано 9» нельзя свести с «вернулось 5», и непонятно, где
;; именно состояния потерялись -- при снятии или при возврате.
(defun KG-DefNestedVisOf (defname / inner states p out dropped)
  (setq inner (KG-Safe '(lambda () (KG_DefEntNames defname)) nil))
  (setq out nil)
  (setq dropped 0)
  (if inner
    (progn
      (setq states (KG-Safe '(lambda () (KG-DefNestedVisibility defname)) nil))
      (foreach p states
        (if (and (car p) (/= (KG-AsString (car p)) "") (cdr p)
                 (/= (KG-AsString (cdr p)) ""))
          (setq out (cons p out))
        )
      )
      ;; Считается от числа вложенных вставок, а не от числа пар без
      ;; состояния: чтение свойств может вообще не отдать пару для вставки,
      ;; у которой нет параметра видимости, и тогда пропуск был бы не виден.
      (setq dropped (- (length inner) (length out)))
      (if (< dropped 0) (setq dropped 0))
    )
  )
  (list (reverse out) dropped)
)

;; Снимок состояний по всем определениям чертежа. Делается ДО освобождения
;; имён: после переименования определение живёт под служебным именем, а
;; состояние нужно привязать к прежнему.
(defun KG-SaveNestedVis ( / names nm got states dropped n kg-t0)
  (setq KG-NESTSAVE nil)
  (setq KG-NESTSAVEN 0)
  (setq KG-NESTDROP 0)
  (setq names (KG-Safe '(lambda () (KG_EXAllDefNames)) nil))
  (setq n 0)
  (foreach nm names
    (if (and (> (length names) 100) (= (rem n 100) 0))
      (KG-Mark (strcat "снимок состояний: пройдено " (itoa n) " из "
                       (itoa (length names))))
    )
    (setq n (1+ n))
    (if (and nm (/= (KG-AsString nm) ""))
      (progn
        (setq kg-t0 (KG-SubT0))
        (setq got (KG-DefNestedVisOf nm))
        (KG-SubT1 "снимок: состояния одного определения" kg-t0)
        (setq states (nth 0 got))
        (setq dropped (KG-AsNum (nth 1 got) 0))
        (setq KG-NESTDROP (+ KG-NESTDROP dropped))
        (if states
          (progn
            (setq KG-NESTSAVE (cons (cons (KG-AsString nm) states) KG-NESTSAVE))
            (setq KG-NESTSAVEN (+ KG-NESTSAVEN (length states)))
          )
        )
      )
    )
  )
  (setq KG-NESTSAVE (reverse KG-NESTSAVE))
  (KG-Mark (strcat "снимок состояний вложенных блоков: определений "
                   (KG-NumStr (length KG-NESTSAVE)) ", состояний "
                   (KG-NumStr KG-NESTSAVEN)
                   (if (> KG-NESTDROP 0)
                     (strcat ", без параметра видимости "
                             (KG-NumStr KG-NESTDROP))
                     "")))
  KG-NESTSAVE
)

;; Вернуть состояния одному определению. Отдаёт список из трёх чисел:
;; возвращено, не найдено в новом определении, не записалось.
;; Прочитать состояние обратно. Нужна отдельно: запись свойства через
;; vlax-put-property может вернуть успех и ничего не изменить -- вложение
;; лежит внутри определения, и AutoCAD не обязан применять к нему
;; динамическое свойство так же, как применяет к экземпляру в модели.
;; «Вернулось 5» без этой проверки означало «вызов прошёл», а не «состояние
;; стоит».
(defun KG-VerifyNestedVis (sub expected / v)
  (setq v (KG-Safe '(lambda () (KG-GetVisibilityState sub)) nil))
  (and v (KG-StrEq v expected))
)

;; Состояние одной вложенной вставки одним значением -- для подробной печати.
(defun KG-VisDetailOne (sub expect / v)
  (setq v (KG-AsString (KG-Safe '(lambda () (KG-GetVisibilityState sub)) "?")))
  (strcat "=\"" (KG-AsString expect) "\" -> \"" v "\"")
)

;; Вернуть состояния одному определению. Отдаёт список:
;;   0 -- возвращено и подтверждено чтением
;;   1 -- не найдено в новом определении
;;   2 -- записать не удалось
;;   3 -- записано, но чтение показало другое
;;   4 -- подробности: ("вложенный=\"прежнее\" -> \"стало\"" ...)
(defun KG-RestoreNestedVisOne (defname states / sub r ok nf bad bad2 st det
                                          keys map kg-t0)
  (setq ok 0 nf 0 bad 0 bad2 0 det nil)
  ;; 71.5. Все вставки ищутся ОДНИМ обходом определения (см.
  ;; KG-DefInsertsForKeys): прежний вариант обходил сборку заново на
  ;; каждое состояние, и каждый такой обход читал EffectiveName у каждой
  ;; вставки через COM. Именно на этом шаг «возврат состояний вложенных
  ;; блоков» стоил 24.9 с живого прогона 71.4.
  (setq keys nil)
  (foreach st states
    (setq keys (cons (KG-AsString (car st)) keys))
  )
  (setq keys (reverse keys))
  (setq kg-t0 (KG-SubT0))
  (setq map (KG-Safe '(lambda () (KG-DefInsertsForKeys defname keys)) nil))
  (KG-SubT1 "возврат: поиск вставок (обход определения)" kg-t0)
  (foreach st states
    ;; Лямбды здесь ссылаются на АРГУМЕНТЫ функции, а не на переменные цикла
    ;; вызывающей функции: такие перехват подставляет.
    (setq sub (cdr (assoc (KG-AsString (car st)) map)))
    (if (null sub)
      (setq nf (1+ nf))
      (progn
        (setq r (KG-Safe '(lambda () (KG-SetVisibilityState sub (cdr st))) nil))
        (if (null r)
          (setq bad (1+ bad))
          (if (KG-VerifyNestedVis sub (cdr st))
            (progn
              (setq ok (1+ ok))
              (setq det
                (cons (strcat (KG-AsString (car st))
                              (KG-VisDetailOne sub (cdr st)))
                      det))
            )
            (progn
              (setq bad2 (1+ bad2))
              (setq det
                (cons (strcat (KG-AsString (car st))
                              (KG-VisDetailOne sub (cdr st)) " НЕ ПРИНЯТО")
                      det))
            )
          )
        )
      )
    )
  )
  (list ok nf bad bad2 (reverse det))
)

;; Поиск сохранённых состояний вложенных динамических блоков для варианта семейства.
;; Источники:
;; 1. Экземпляры этого варианта из плана интеграции (groups / instances).
;; 2. Старые определения этого варианта из снимка KG-NESTSAVE.
(defun KG-FindVariantNestedStates (base v plan / groups grp pr inst st p hit)
  (setq st nil hit nil)
  ;; 1. Из групп экземпляров плана
  (if (and plan (assoc "scan" plan))
    (progn
      (setq groups (cdr (assoc "groups" (cdr (assoc "scan" plan)))))
      (setq grp (vl-some '(lambda (g) (if (KG-StrEq (car g) v) g nil)) groups))
      (if grp
        (progn
          (setq pr (car (cdr grp)))
          (if pr
            (progn
              (setq inst (car pr))
              (if inst
                (setq st (KG-CdrCI "nested-vis" inst))
              )
            )
          )
        )
      )
    )
  )
  ;; 1b. Из списка всех старых экземпляров плана (если группы не дали)
  (if (and (null st) plan (assoc "instances" plan))
    (foreach pr (cdr (assoc "instances" plan))
      (if (and (null st) (KG-StrEq (nth 2 (cdr pr)) v))
        (setq st (KG-CdrCI "nested-vis" (car pr)))
      )
    )
  )
  ;; 2. Если вхождения не дали состояний (или экземпляров не было), ищем в KG-NESTSAVE
  (if (and (null st) KG-NESTSAVE)
    (foreach entry KG-NESTSAVE
      (if (not hit)
        (progn
          (setq p (KG-ParseBlockName (car entry)))
          (if (and p (KG-StrEq (nth 0 p) base) (KG-StrEq (nth 2 p) v))
            (setq hit (cdr entry))
          )
        )
      )
    )
  )
  (if st st hit)
)

;; Одно определение из списка переименований. Отдельная функция по той же
;; причине, что KG-RewirePairOf: у лямбды под KG-Safe подстановка
;; динамическая, и свободная переменная с ходовым именем (r, fn, def, msg)
;; тихо берётся из рамки KG-Safe. Значение сюда передаётся обычным
;; аргументом -- это надёжно.
;;
;; Шестой элемент результата -- имя определения, когда в него хоть что-то
;; возвращено: отчёт должен называть определения, а не только количество.
(defun KG-RestoreVisOfPair (r / nm st res p base variant cand targetnm curplan
                              kg-t0 kg-ex)
  ;; 71.6. Суб-замеры: строка «возврат состояний вложенных блоков» не
  ;; говорила, где именно её время. Каждый шаг этой функции меряется
  ;; отдельно, повторная проверка имени цели -- тоже: targetnm уже
  ;; проверен выше, и здесь видно, сколько стоит сам повтор.
  (setq nm (KG-AsString (nth 0 r)))
  (setq kg-t0 (KG-SubT0))
  (setq st (KG-CdrCI nm KG-NESTSAVE))
  (KG-SubT1 "возврат: состояния из снимка" kg-t0)
  (setq curplan (if (and (boundp 'plan) plan) plan KG-PLAN))
  ;; Определение может существовать под прежним именем (например, блок без
  ;; версии «Закладная в полость стойки»).
  ;; Если определение под прежним именем не существует, но имя принадлежит
  ;; старому варианту семейства, ищем новое определение варианта новой итерации.
  (setq kg-t0 (KG-SubT0))
  (setq targetnm
    (cond
      ((KG_EXDefExists nm) nm)
      (curplan
       (setq p (KG-ParseBlockName nm))
       (if (and p (KG-StrEq (nth 0 p) (cdr (assoc "family" curplan))))
         (progn
           (setq variant (nth 2 p))
           (setq cand (KG-MakeName (nth 0 p) (cdr (assoc "newiter" curplan)) variant))
           (if (and (/= (KG-AsString variant) "") (KG_EXDefExists cand)) cand nil)
         )
         nil
       ))
      (t nil)
    ))
  (KG-SubT1 "возврат: выбор цели" kg-t0)
  (setq kg-t0 (KG-SubT0))
  (setq kg-ex (and targetnm (KG_EXDefExists targetnm)))
  (KG-SubT1 "возврат: проверка цели (повтор)" kg-t0)
  (if kg-ex
    (progn
      (setq kg-t0 (KG-SubT0))
      (if (null st)
        (if (and curplan (setq p (KG-ParseBlockName targetnm))
                 (KG-StrEq (nth 0 p) (cdr (assoc "family" curplan))))
          (setq st (KG-FindVariantNestedStates (nth 0 p) (nth 2 p) curplan))
        )
      )
      (KG-SubT1 "возврат: состояния варианта" kg-t0)
      (if st
        (progn
          (setq kg-t0 (KG-SubT0))
          (setq res (KG-RestoreNestedVisOne targetnm st))
          (KG-SubT1 "возврат: запись состояний" kg-t0)
          (if (> (KG-AsNum (nth 0 res) 0) 0)
            (append res (list targetnm))
            res
          )
        )
        (list 0 0 0 0 nil)
      )
    )
    (list 0 0 0 0 nil)
  )
)

;; Шаг 8в. Вернуть состояния видимости вложенных блоков определениям, которые
;; были подменены пришедшими из буфера, а также определениям вариантов семейства.
(defun KG-Step_RestoreNestedVis (renames / r res restored notfound failed
                                         unconf ndefs defs dets n curplan
                                         base newiter allvars v nm st
                                         kg-t0 kg-ex)
  (setq restored 0 notfound 0 failed 0 unconf 0 ndefs 0)
  (setq defs nil dets nil)
  (setq n 0)
  ;; 1. Обработка переименованных определений
  (foreach r renames
    (if (and (> (length renames) 100) (= (rem n 100) 0))
      (KG-Mark (strcat "возврат состояний: пройдено " (itoa n) " из "
                       (itoa (length renames))))
    )
    (setq n (1+ n))
    (setq kg-t0 (KG-SubT0))
    (setq res (KG-RestoreVisOfPair r))
    (KG-SubT1 "возврат: разбор пары (всего)" kg-t0)
    (if (nth 5 res)
      (if (not (member (nth 5 res) defs))
        (progn
          (setq restored (+ restored (KG-AsNum (nth 0 res) 0)))
          (setq notfound (+ notfound (KG-AsNum (nth 1 res) 0)))
          (setq failed (+ failed (KG-AsNum (nth 2 res) 0)))
          (setq unconf (+ unconf (KG-AsNum (nth 3 res) 0)))
          (setq ndefs (1+ ndefs))
          (setq defs (cons (nth 5 res) defs))
          (if (nth 4 res) (setq dets (append dets (nth 4 res))))
        )
      )
      (progn
        (setq restored (+ restored (KG-AsNum (nth 0 res) 0)))
        (setq notfound (+ notfound (KG-AsNum (nth 1 res) 0)))
        (setq failed (+ failed (KG-AsNum (nth 2 res) 0)))
        (setq unconf (+ unconf (KG-AsNum (nth 3 res) 0)))
        (if (nth 4 res) (setq dets (append dets (nth 4 res))))
      )
    )
  )
  ;; 2. Дополнительная проверка всех определений вариантов семейства из плана
  (setq curplan (if (and (boundp 'plan) plan) plan KG-PLAN))
  (if curplan
    (progn
      (setq base (cdr (assoc "family" curplan)))
      (setq newiter (cdr (assoc "newiter" curplan)))
      (setq allvars
        (KG-Unique
          (append (cdr (assoc "variants-to-create" curplan))
                  (cdr (assoc "variants-existing" curplan)))))
      (foreach v allvars
        (if (and v (/= (KG-AsString v) ""))
          (progn
            (setq nm (KG-MakeName base newiter v))
            (setq kg-t0 (KG-SubT0))
            (setq kg-ex (KG_EXDefExists nm))
            (KG-SubT1 "возврат: проверка имени варианта" kg-t0)
            (if (and kg-ex (not (member nm defs)))
              (progn
                (setq kg-t0 (KG-SubT0))
                (setq st (KG-FindVariantNestedStates base v curplan))
                (KG-SubT1 "возврат: состояния варианта" kg-t0)
                (if st
                  (progn
                    (setq kg-t0 (KG-SubT0))
                    (setq res (KG-RestoreNestedVisOne nm st))
                    (KG-SubT1 "возврат: запись состояний" kg-t0)
                    (if (> (KG-AsNum (nth 0 res) 0) 0)
                      (progn
                        (setq restored (+ restored (KG-AsNum (nth 0 res) 0)))
                        (setq notfound (+ notfound (KG-AsNum (nth 1 res) 0)))
                        (setq failed (+ failed (KG-AsNum (nth 2 res) 0)))
                        (setq unconf (+ unconf (KG-AsNum (nth 3 res) 0)))
                        (setq ndefs (1+ ndefs))
                        (setq defs (cons nm defs))
                        (if (nth 4 res) (setq dets (append dets (nth 4 res))))
                      )
                    )
                  )
                )
              )
            )
          )
        )
      )
    )
  )
  (KG-Mark (strcat "возвращено состояний вложенных блоков: "
                   (KG-NumStr restored) " в определениях "
                   (KG-NumStr ndefs)))
  (if (> notfound 0)
    (princ (strcat "\nВНИМАНИЕ: " (itoa notfound)
                   " состояний вложенных блоков не возвращены -- такого "
                   "вложенного блока в новой версии нет.")))
  (if (> failed 0)
    (princ (strcat "\nВНИМАНИЕ: " (itoa failed)
                   " состояний вложенных блоков записать не удалось.")))
  ;; Запись не подтвердилась чтением. Это главный признак того, что AutoCAD
  ;; принял вызов, но состояние не применил: без этой строки «вернулось 5»
  ;; означало бы «вызов прошёл», а на чертеже осталось значение мастер-блока.
  (if (> unconf 0)
    (princ (strcat "\nВНИМАНИЕ: " (itoa unconf)
                   " состояний вложенных блоков записаны, но чтение "
                   "показало другое значение -- состояние НЕ применено.")))
  (if defs
    (princ (strcat "\nСостояния возвращены в определения: "
                   (KG-JoinNames (reverse defs)))))
  (foreach x dets
    (KG-TraceDetail (strcat "состояние " x)))
  ;; 0 возвращено, 1 не найдено, 2 не записалось, 3 не подтвердилось,
  ;; 4 число определений, 5 определения, 6 подробности.
  (list restored notfound failed unconf ndefs (reverse defs) dets)
)

;; Есть ли в чертеже многострочная вставка (MINSERT) этого определения.
;; MINSERT тоже держит определение, а в подсчёт ссылок он не входит,
;; поэтому при его наличии *U не стираем.
(defun KG_HasMInsert (defname / e ed hit)
  ;; Есть ли ВНУТРИ определения многострочная вставка (MINSERT): её
  ;; нельзя расчленить, и определение с ней стирать не следует.
  ;;
  ;; ПРЕЖНЯЯ ПРОВЕРКА БЛОКИРОВАЛА ВСЁ. Она искала ssget'ом вставки с
  ;; признаком атрибутов ((66 . 1)) и именем определения. Анонимное
  ;; представление динамического блока почти всегда несёт атрибуты --
  ;; тег представления (AcDbBlockRepBTag) хранится именно так. Поэтому
  ;; проверка отвечала «да» на все 43 сироты, ENTD не вызывался ни разу,
  ;; и очистка печатала «Стёрто 0, не удалось 43». Многострочная вставка
  ;; -- это другое: группа 0 равна "MINSERT", и лежит она внутри самого
  ;; определения, поэтому искать её нужно обходом содержимого.
  (setq hit nil)
  (setq e (KG-Safe '(lambda () (KG-DefEnt defname)) nil))
  (while (and (not hit)
              e
              (setq e (KG-Safe '(lambda () (entnext e)) nil))
              (setq ed (KG-Safe '(lambda () (entget e)) nil))
              (/= (KG-AsString (cdr (assoc 0 ed))) "ENDBLK"))
    (if (KG-StrEq (KG-AsString (cdr (assoc 0 ed))) "MINSERT") (setq hit t))
  )
  hit
)

;; Есть ли в чертеже определения, пришедшие из внешней ссылки. Пока они
;; есть, содержимое чертежа связано с внешним файлом и *U не стираются
;; (п. «XREF не обрабатываем»).
(defun KG_HasXrefDefs ( / tbl out)
  (setq out nil)
  (setq tbl (KG-Safe '(lambda () (tblnext "BLOCK" t)) nil))
  (while tbl
    (if (KG-IsXrefDepName (KG-AsString (cdr (assoc 2 tbl))))
      (setq out t tbl nil)
      (setq tbl (KG-Safe '(lambda () (tblnext "BLOCK")) nil))
    )
  )
  out
)

;; Стирание одного сиротского *U: ENTD по записи таблицы блоков.
;; Возвращает T, если определение исчезло.
(defun KG_EXEraseAnonDef (defname / e r ok n)
  (setq ok nil n 0)
  (setq KG-ERASE-WHY "")
  (setq KG-ERASE-ERR "")
  (if (KG-Safe '(lambda () (KG_HasMInsert defname)) nil)
    ;; без этой строки отказ выглядел как «не удалось: 43» без причины
    (progn
      (setq KG-ERASE-WHY "minsert")
      (KG-TraceDetail (strcat "стирание \"" (KG-AsString defname)
                              "\": внутри есть многострочная вставка"))
    )
    (progn
      (setq e (KG-Safe '(lambda () (KG-DefEnt defname)) nil))
      ;; ENTD целится ТОЛЬКО в запись определения: живой прогон сборки 71
      ;; показал, что прежний код получал из tblsearch первый объект ВНУТРИ
      ;; определения и стирал не блок, а его первый примитив.
      (if (not (KG-DefRecEnt e)) (setq e nil))
      (if e
        (progn
          ;; vl-catch-all-apply напрямую, а не KG-Call: если ENTD отказал
          ;; С ОШИБКОЙ, её текст -- единственное, что объясняет отказ, а
          ;; KG-Call ошибку возвращает запасным значением и текст теряет.
          (setq r (vl-catch-all-apply 'entdel (list e)))
          (if (KG-IsErr r)
            (progn
              (setq KG-ERASE-ERR (KG-AsString (vl-catch-all-error-message r)))
              (setq r nil)
            )
          )
          (if r
            (progn
              ;; определение должно исчезнуть; если ename ещё читается,
              ;; стирание не состоялось
              (while (and (< n 3)
                          (KG-Safe '(lambda () (KG-DefEnt defname)) nil))
                (setq n (1+ n))
              )
              (setq ok (not (KG-Safe '(lambda () (KG-DefEnt defname)) nil)))
              (if (not ok) (setq KG-ERASE-WHY "left"))
            )
            (progn
              (setq KG-ERASE-WHY "entdel")
              ;; Текст прежней метки («BLOCK не найден») вводил в заблуждение:
              ;; ename к этому моменту найден, не отдался именно ENTD. В
              ;; прогоне сборки 54 строка «нет BLOCK для ...» не появилась ни
              ;; разу -- значит, поиск определения работал, а читался отказ
              ;; как «определения нет».
              (KG-TraceDetail (strcat "стирание \"" (KG-AsString defname)
                                      "\": ENTD не отдал определение"))
            )
          )
        )
        (progn
          (setq KG-ERASE-WHY "noent")
          (KG-TraceDetail (strcat "стирание \"" (KG-AsString defname)
                                  "\": не найден ename определения"))
        )
      )
      (if (and r (not ok))
        (KG-TraceDetail (strcat "стирание \"" (KG-AsString defname)
                                "\": определение читается и после ENTD"))
      )
      (if ok (setq KG-ERASE-WHY "ok"))
      ok
    )
  )
)

;; --- Разбор держателей остатка ---------------------------------------------
;; Почему определение не убирается: PURGE считает его использованным, а ENTD
;; отказывает. Строка «держит: (прямых вставок нет)» верна, но не объясняет:
;; вставок нет, а ссылка есть -- в словаре самого определения. Живой прогон
;; сборки 71 оставил ровно так 20 определений «~ИМЯ» и 19 представлений
;; «*U». Пробы ниже -- только чтение: без разбора словарей удаление вслепую
;; уже роняло проверку (vla-Delete дал 0xC0000005).

;; Как называется то, на что указывает handle: имя определения, тип записи
;; или сам handle. Читается по одной записи, без обходов таблицы.
(defun KG-RefObjLabel (h / ed z nm)
  (setq ed (KG-Call 'entget (list h) nil))
  (setq z (KG-AsString (cdr (assoc 0 ed))))
  (setq nm (KG-AsString (cdr (assoc 2 ed))))
  (cond
    ((and nm (/= nm "")) nm)
    ((/= z "") z)
    (t (strcat "#" (KG-AsString h)))
  )
)

;; Запись словаря одной строкой: «ключ»->значение. nil -- запись нечитаема.
(defun KG-DictEntryText (e / key hd)
  (setq key (KG-AsString (cdr (assoc 3 e))))
  (setq hd (cdr (assoc 360 e)))
  (if (null hd) (setq hd (cdr (assoc 350 e))))
  (if (/= key "")
    (strcat "«" key "»->" (if hd (KG-RefObjLabel hd) "?"))
    nil
  )
)

;; Что лежит в словаре записи определения. Сначала перебор словаря по 360
;; через dictnext, затем известные ключи динамических блоков напрямую через
;; dictsearch: ACAD_ENHANCEDBLOCK -- данные динамического блока (оттуда же
;; читается имя параметра видимости), AcDbBlockRepBTag -- метка, которой
;; представление (*U) держится за родительское определение. Пусто -- словаря
;; не видно.
(defun KG-DefDictProbe (defname / rec ed xd e txt n part hd key)
  (setq txt "")
  (setq rec (KG-Call 'KG-DefEnt (list defname) nil))
  (if rec
    (progn
      (setq ed (KG-Call 'entget (list rec) nil))
      (setq xd (cdr (assoc 360 ed)))
      (if xd
        (progn
          ;; dictnext после перевода отдаёт первую запись; если реализация
          ;; отвечает nil, добираем её обычным вызовом.
          (setq e (KG-Call 'dictnext (list xd t) nil))
          (if (null e) (setq e (KG-Call 'dictnext (list xd) nil)))
          (setq n 0)
          (while (and e (< n 4))
            (setq part (KG-DictEntryText e))
            (if part
              (setq txt (strcat txt (if (= txt "") "" ", ") part))
            )
            (setq n (1+ n))
            (setq e (KG-Call 'dictnext (list xd) nil))
          )
          (if e (setq txt (strcat txt ", …")))
        )
      )
      (foreach key (list "ACAD_ENHANCEDBLOCK" "AcDbBlockRepBTag")
        (setq part (KG-Call 'dictsearch (list ed key) nil))
        (if part
          (progn
            (setq hd (cdr (assoc 360 part)))
            (if (null hd) (setq hd (cdr (assoc 350 part))))
            (if (not (KG-StrPos key txt))
              (setq txt (strcat txt (if (= txt "") "" ", ")
                                "«" key "»->"
                                (if hd (KG-RefObjLabel hd) "?")))
            )
          )
        )
      )
    )
  )
  txt
)

;; Стирать ли сиротские *U. Отдельный предикат, а не условие внутри
;; KG-CleanupRun: KG-CleanupRun исполняется только в AutoCAD, а решение
;; должно быть проверяемым на стенде. Три причины не стирать: выключен
;; переключатель, стирать нечего, в чертеже есть определения из внешней
;; ссылки (их содержимое связано с внешним файлом, п. «XREF не
;; обрабатываем»).
(defun KG-OwnerBlockName (e / ed oh)
  (if (or (null e) (= (type e) (type "")))
    nil
    (progn
      (setq ed (entget e))
      (setq oh (if ed (cdr (assoc 330 ed)) nil))
      (if oh (KG-RecordNameOf oh) nil)
    )
  )
)

;; Имя записи блока по её handle (группа 2)
(defun KG-RecordNameOf (oh / oe ed)
  (setq oe (if oh (handent (KG-AsString oh)) nil))
  (setq ed (if oe (entget oe) nil))
  (if ed (KG-AsString (cdr (assoc 2 ed))) nil)
)

;;;--- Чтение модели чертежа -------------------------------------------------

;; Список динамических свойств экземпляра: (("Имя" . значение) ...)

(defun KG-EXRefHolders ( / out ss i n e ed tgt defnm flt oh pr v hx kg-t0)
  ;; Карта ссылок «определение -> кто его вставляет».
  ;;
  ;; ПРЕЖНИЙ СПОСОБ УБИВАЛ КОМАНДУ: обход таблицы блоков с
  ;; tblobjname + entnext + entget по каждому определению на реальном
  ;; чертеже дал 0xC0000005 после того, как из буфера пришли 109
  ;; определений, а 48 были переименованы. Перехват исключение не ловит.
  ;;
  ;; Теперь -- выборка вставок через ssget "_X" и группа 330 у каждой:
  ;; она указывает на запись блока, внутри которой вставка лежит. Ни COM,
  ;; ни обхода таблицы блоков.
  ;;
  ;; Результат -- ("OK" . карта): маркер в car, карта в cdr, nil --
  ;; выборка не сработала. Маркер ЭЛЕМЕНТОМ списка быть не должен:
  ;; KG-CdrCI ищет по списку и на строке «OK» отвечал «нашёл», из-за чего
  ;; любое имя считалось присутствующим в карте, а сама карта при этом
  ;; терялась -- в сборке 38 на диск ушла именно такая версия.
  (KG-TraceDetail "карта ссылок: выборка всех вставок")
  (setq kg-t0 (KG-SubT0))
  (setq out nil)
  (setq ss (KG-Call 'ssget (list "_X" (list (cons 0 "INSERT"))) nil))
  (if (KG-IsErr ss)
    (KG-Mark (strcat "карта ссылок: выборка с фильтром отказала: "
                     (KG-AsString
                       (KG-Safe '(lambda () (vl-catch-all-error-message ss))
                                "?"))))
    (KG-TraceDetail (strcat "карта ссылок: выборка с фильтром дала "
                     (if ss "набор" "nil")))
  )
  (if (KG-IsErr ss) (setq ss nil))
  (setq flt t)
  (if (null ss)
    ;; На реальном чертеже выборка с фильтром ((0 . "INSERT")) вернула
    ;; nil при трёх живых вставках, и очистка остановилась. Запасной
    ;; путь -- выборка без фильтра и своя проверка группы 0: дороже, но
    ;; не зависит от того, как AutoCAD обработал фильтр.
    (progn
      (KG-Mark "карта ссылок: запасная выборка без фильтра")
      ;; вторым аргументом nil, а не «без аргумента»: в AutoCAD
      ;; отсутствующий аргумент принимает nil, но полагаться на это не
      ;; стоит -- функция, читающая flt, спотыкается о неопределённую
      ;; переменную.
      (setq ss (KG-Call 'ssget (list "_X" nil) nil))
      (if (KG-IsErr ss) (setq ss nil))
      (setq flt nil)
    )
  )
  (if ss
    (progn
      (setq n (KG-AsNum (KG-Call 'sslength (list ss) 0) 0))
      (KG-TraceDetail (strcat "карта ссылок: объектов в наборе " (itoa n)))
      ;; Промежуточный счёт каждые 200 объектов. Прогон на крупном
      ;; реципиенте (1231 вставка) оборвался с 0xC0000005 сразу после
      ;; строки «объектов в наборе 1231» -- без промежуточных меток
      ;; неизвестно, дошёл ли обход до конца и на каком объекте встал.
      (setq KG-REFDONE 0)
      (setq KG-REFCACHE nil)
      (setq i 0)
      (while (< i n)
        (if (and (> n 200) (= (rem i 200) 0))
          (KG-Mark (strcat "карта ссылок: пройдено " (itoa i) " из "
                           (itoa n)))
        )
        (setq e (KG-Call 'ssname (list ss i) nil))
        (if e
          (progn
            (setq ed (KG-Call 'entget (list e) nil))
            (if ed
              (progn
                ;; без фильтра в наборе все примитивы -- берём вставки
                (if (not flt)
                  (if (not (KG-StrEq (KG-AsString (cdr (assoc 0 ed)))
                                     "INSERT"))
                    (setq ed nil)
                  )
                )
                (if ed
                  (progn
                    (setq tgt (KG-AsString (cdr (assoc 2 ed))))
                    ;; Имя владельца -- из кэша по handle. handent на
                    ;; крупном чертеже после PURGE даёт 0xC0000005, а
                    ;; перехват его не ловит: в прогоне на 1231 вставке
                    ;; INTBRIEF оборвалась именно здесь. Повторных
                    ;; обращений к одному владельцу при этом в десятки
                    ;; раз больше, чем самих владельцев.
                    (setq defnm
                      (KG-Safe
                        '(lambda ()
                           (setq oh (cdr (assoc 330 ed)))
                           (setq oh (if oh (KG-AsString oh) ""))
                           (setq pr (assoc oh KG-REFCACHE))
                           (if pr
                             (cdr pr)
                             (progn
                               (setq v (KG-OwnerBlockName e))
                               (setq KG-REFCACHE
                                 (cons (cons oh v) KG-REFCACHE))
                               v)))
                        nil))
                    (setq KG-REFDONE (1+ KG-REFDONE))
                    ;; Владелец не прочитался -- ссылку всё равно
                    ;; считаем: лучше держатель «неизвестно», чем объявить
                    ;; определение свободным и снять его.
                    (if (/= tgt "")
                      (setq out
                        (KG-RMSet tgt
                          (cons (if defnm defnm "неизвестно")
                                (KG-RMCdr tgt out))
                          out))
                    )
                    ;; Скрытые ссылки экземпляра: представление (*U)
                    ;; держится не группой 2, а xdata/словарём самого
                    ;; экземпляра. Без этого чтения живое представление
                    ;; выглядело сиротой, и стирание сломало бы живой
                    ;; экземпляр. Имена -- в ту же карту, с тем же
                    ;; владельцем.
                    (foreach hx (KG-Call 'KG-HiddenRefNames (list ed) nil)
                      (if (/= (KG-AsString hx) "")
                        (setq out
                          (KG-RMSet (KG-AsString hx)
                            (cons (if defnm defnm "неизвестно")
                                  (KG-RMCdr (KG-AsString hx) out))
                            out))
                      )
                    )
                  )
                )
              )
            )
          )
        )
        (setq i (1+ i))
      )
      (KG-TraceDetail (strcat "карта ссылок: пройдено объектов "
                       (KG-NumStr KG-REFDONE) " из " (itoa n)))
      (setq out (cons "OK" out))
    )
  )
  (KG-SubT1 "карта ссылок (обход вставок)" kg-t0)
  out
)

;; Имена, на которые экземпляр ссылается СКРЫТО. Представление (*U)
;; динамического блока держится экземпляром не группой 2, а xdata (1005)
;; и/или словарём экземпляра (360 -> записи 350/360). Прогон сборки 71:
;; очистка считала такое представление сиротой (вставок с его именем в
;; чертеже нет) и пыталась стереть -- живой экземпляр мог потерять своё
;; представление. Теперь скрытые имена попадают в карту ссылок, и живое
;; представление сиротой не выглядит.
(defun KG-ResolveRefName (v)
  ;; Значение ссылки -- строка-handle или ename. Отдаём имя определения.
  (cond
    ((null v) nil)
    ((= (type v) (type "")) (KG-RecordNameOf (KG-AsString v)))
    (t (KG-Safe '(lambda () (KG-AsString (cdr (assoc 2 (entget v))))) nil))
  )
)

;; ename по строке-handle; уже ename возвращается как есть.
(defun KG-RefEntOf (v)
  (cond
    ((null v) nil)
    ((= (type v) (type "")) (KG-Safe '(lambda () (handent (KG-AsString v))) nil))
    (t v)
  )
)

;; Имена из словаря (записи 350 и вложенные словари 360). Глубина
;; ограничена: глубже -- уже не словарь экземпляра.
(defun KG-DictRefNames (d dep / out de v q x)
  (setq out nil)
  (if (and d (> dep 0))
    (progn
      (setq de (KG-Safe '(lambda () (entget d)) nil))
      (foreach v de
        (if (and (not (= (type v) (type "")))
                 (= (car v) 350))
          (progn
            (setq q (KG-ResolveRefName (cdr v)))
            (if q (setq out (cons q out)))
          )
        )
        (if (and (not (= (type v) (type "")))
                 (= (car v) 360))
          (progn
            (setq q (KG-RefEntOf (cdr v)))
            (foreach x (KG-DictRefNames q (1- dep))
              (setq out (cons x out))
            )
          )
        )
      )
    )
  )
  out
)

;; Скрытые ссылки экземпляра: xdata (1005) + словарь (360).
(defun KG-HiddenRefNames (ed / out x v q)
  (setq out nil)
  (foreach x (cdr (assoc -3 ed))
    (if (not (= (type x) (type "")))
      (foreach v x
        (if (and (not (= (type v) (type "")))
                 (= (car v) 1005))
          (progn
            (setq q (KG-ResolveRefName (cdr v)))
            (if q (setq out (cons q out)))
          )
        )
      )
    )
  )
  (foreach v (KG-DictRefNames (KG-RefEntOf (cdr (assoc 360 ed))) 3)
    (setq out (cons v out))
  )
  (KG-Unique out)
)

(defun KG-CleanupEraseAllowed (flag orph noxref)
  (and flag (if orph t nil) noxref)
)

(defun KG-DBX-Fail (msg)
  (setq KG-DBX-ERR (cons msg KG-DBX-ERR))
  nil
)

;; Выполнить под перехватом; при неудаче записать шаг и текст ошибки.
;; Лямбда КВОТИРОВАННАЯ: вычисленная в AutoCAD превращается в SUBR и
;; vl-catch-all-apply её отвергает.
(defun KG-DBX-Try (kg-step kg-fn / kg-res)
  (setq kg-res (vl-catch-all-apply kg-fn))
  (if (KG-IsErr kg-res)
    (KG-DBX-Fail (strcat kg-step ": "
                         (KG-AsString (vl-catch-all-error-message kg-res))))
    kg-res
  )
)

(defun KG-MasterState (mastername beforedefs arrived)
  (cond
    ((not mastername) "не определена")
    ((not (KG-StrInterCI (list mastername) beforedefs))
     "пришла из буфера как новое определение")
    ((KG-StrInterCI (list mastername) arrived)
     "перезаписана из буфера (имя уже было в чертеже)")
    (t "ОСТАЛАСЬ СТАРОЙ: имя было в чертеже, буфер его не принёс")
  )
)

;; Определения, которые нужно переименовать ДО вставки из буфера.
;;
;; Причина: PASTECLIP НЕ переименовывает конфликтующие определения --
;; он печатает "Duplicate definition of block ... ignored" и оставляет
;; в чертеже СТАРОЕ определение. Поэтому имена освобождаются заранее.
;;
;; Кандидаты -- все неанонимные определения, достижимые из определений
;; семейства base любых итераций (то есть всё, что может прийти вместе
;; с новой мастер-версией под тем же именем).
(defun KG-ConflictCandidates (model base / out nm)
  (setq out nil)
  (foreach nm (KG-UserDefNames model)
    (if (KG-IsFamilyName nm base)
      (foreach c (KG-GetNestedBlocks model nm)
        (setq out (cons c out))
      )
    )
  )
  (KG-Unique
    (vl-remove-if
      '(lambda (x) (or (null x) (= x "")
                       (KG-IsSystemBlockName x)
                       (KG-IsFamilyName x base)))
      out))
)

;;; Освободить имя мастер-версии до вставки из буфера.
;;; Возвращает пару (старое-имя . временное-имя) или nil, если имя и так
;;; свободно. Пара нужна, чтобы при неудачной вставке вернуть имя на место.
(defun KG-FreeMasterName (mastername newiter / tmp used)
  (if (not (KG_EXDefExists mastername))
    nil
    (progn
      (setq used (KG_EXAllDefNames))
      (setq tmp (KG-TempDefName mastername newiter used))
      (if (KG_EXRenameDef mastername tmp)
        (progn
          (KG-Mark (strcat "имя мастер-версии освобождено: " mastername
                            " -> " tmp))
          (princ (strcat "\nОпределение \"" mastername
                         "\" временно переименовано в \"" tmp
                         "\", чтобы освободить имя для вставки из буфера."))
          (cons mastername tmp))
        (progn
          (princ (strcat "\nОШИБКА: не удалось освободить имя \"" mastername
                         "\". AutoCAD отбросит пришедшее определение."))
          nil))
    )
  )
)

;; Вернуть имя мастер-версии, если вставка из буфера не удалась
(defun KG-RestoreMasterName (freed / old tmp)
  (setq old (car freed))
  (setq tmp (cdr freed))
  (if (and old tmp (KG_EXDefExists tmp))
    (KG_EXRenameDef tmp old)
    nil
  )
)

;; Определение семейства base, ссылающееся на вложенное nm.
;; Нужно только для осмысленного имени сохраняемого старого определения.
;; Приоритет: вариант семейства с тем же суффиксом (у него «своя» итерация),
;; затем любое определение семейства со ссылкой на nm.
(defun KG-SourceOfNested (model base nm / out p)
  (setq out nil)
  (foreach d (KG-UserDefNames model)
    (if (and (not out)
             (KG-IsFamilyName d base)
             (setq p (KG-ParseBlockName d))
             (KG-StrEq (nth 2 p) nm)
             (vl-some '(lambda (c) (KG-StrEq c nm))
                      (KG-GetNestedBlocks model d)))
      (setq out d)
    )
  )
  (if (not out)
    (foreach d (KG-UserDefNames model)
      (if (and (not out)
               (KG-IsFamilyName d base)
               (vl-some '(lambda (c) (KG-StrEq c nm))
                        (KG-GetNestedBlocks model d)))
        (setq out d)
      )
    )
  )
  out
)

;; 71.6. Карта «вложенное определение -> определение, в которое оно
;; вложено» одним проходом. Прежний KG-SourceOfNested на КАЖДОЕ имя заново
;; обходил все определения семейства: суб-замер 71.5 «пре:
;; определение-источник» показал 5.09 с при 76 вызовах. Пары строятся в том
;; же порядке, что и KG-UserDefNames, поэтому выбор первого подходящего
;; определения не меняется.
(defun KG-NestedPairs (model / out)
  (setq out nil)
  (foreach d (KG-UserDefNames model)
    (foreach c (KG-GetNestedBlocks model d)
      (setq out (cons (cons c d) out))
    )
  )
  (reverse out)
)

;; Определение-источник по готовой карте. Приоритеты KG-SourceOfNested
;; сохранены: сперва вариант семейства, у которого суффикс совпал с именем
;; вложенного, затем любое определение семейства со ссылкой на него.
(defun KG-SourceOfNestedIn (pairs base nm / out d p pr)
  (setq out nil)
  (foreach pr pairs
    (if (and (not out) (KG-StrEq (car pr) nm))
      (progn
        (setq d (cdr pr))
        (if (and (KG-IsFamilyName d base)
                 (setq p (KG-ParseBlockName d))
                 (KG-StrEq (nth 2 p) nm))
          (setq out d)
        )
      )
    )
  )
  (if (not out)
    (foreach pr pairs
      (if (and (not out) (KG-StrEq (car pr) nm)
               (KG-IsFamilyName (cdr pr) base))
        (setq out (cdr pr))
      )
    )
  )
  out
)

;; Правило переноса состояния видимости (п. 9.4 ТЗ, вариант A).
;; Возвращает (list значение признак-совпадения предупреждение)
;; Возвращает (установленное-состояние найдено-ли-старое текст-предупреждения).
;; Если у определения вообще нет состояний видимости (вложенный блок без
;; параметра видимости), восстанавливать нечего: состояние считается
;; восстановленным и предупреждение не выдаётся.
(defun KG-ResolveVisibility (old avail / hit first)
  (cond
    ((or (null avail) (= (length avail) 0))
     (list old t nil))
    (t
     (setq first (nth 0 avail))
     (setq hit (vl-some '(lambda (a) (if (KG-StrEq a old) a nil)) avail))
     (cond
       (hit (list hit t nil))
       ((or (null old) (= old "")) (list first nil nil))
       (t
        (list first nil
              (strcat "Старое состояние \"" (KG-AsString old)
                      "\" отсутствует в новой версии. Установлено состояние \""
                      (KG-AsString first) "\".")))
     ))
  )
)

;; План восстановления видимости одного экземпляра.
;; Возвращает (("Стойка" (новое-значение совпало предупреждение)) ...)
(defun KG-PlanNestedVisibility (model inst newdefname / def states out r)
  (setq def (KG-FindDef model newdefname))
  (setq out nil)
  (foreach pair (KG-CdrCI "nested-vis" inst)
    (setq states (KG-CdrCI "vis-states" (KG-FindDef model (car pair))))
    (if (null states) (setq states (KG-CdrCI "vis-states" def)))
    (setq r (KG-ResolveVisibility (cdr pair) states))
    (setq out (cons (cons (car pair) (list (nth 0 r) (nth 1 r) (nth 2 r))) out))
  )
  (reverse out)
)

;; Карта интеграции (Этап 4).
(defun KG-BuildIntegrationMap (model mastername beforedefs / p base newiter
                                     scan groups nested newnested existing
                                     tocreate toexist torename out dv)
  (setq p (KG-ParseBlockName mastername))
  (if (null p)
    nil
    (progn
      (setq base (nth 0 p))
      (setq newiter (nth 1 p))
      (setq scan (KG-ScanFamily model base newiter))
      (setq groups (cdr (assoc "groups" scan)))
      ;; 71.3: определения семьи без вставок. Сканирование видит только
      ;; экземпляры, поэтому вариант, существующий лишь определением
      ;; («Комплект КП50К стойка КП45370 v1.3» без единой вставки), остался
      ;; бы без новой версии. Он добавляется в группы пустым: определение
      ;; создастся из мастера (или уже есть), вставок по-прежнему ноль.
      (if (KG-FlexFamilyP base newiter)
        (foreach dv (KG-FindOldFamilyDefs model base newiter)
          (if (not (KG-StrInterCI (list (nth 2 (cdr dv)))
                                  (mapcar 'car groups)))
            (setq groups
              (append groups (list (cons (nth 2 (cdr dv)) nil))))
          )
        )
      )
      (setq scan (KG-SetAssoc "groups" groups scan))
      ;; ВАЖНО: классификация «обновить / добавить» считается по снимку
          ;; таблицы блоков ДО вставки. После вставки новые определения уже
          ;; есть в файле, и по текущему состоянию их не отличить от старых.
      (setq newnested (KG-GetNestedBlocks model mastername))
      (if beforedefs
        (setq nested
          (list
            (cons "to-update" (KG-StrInterCI newnested beforedefs))
            (cons "to-add" (KG-StrDiffCI newnested beforedefs))))
        (setq nested (KG-MapNestedBlocks model mastername))
      )
      (setq existing (KG-UserDefNames model))
      (setq tocreate nil toexist nil)
      (foreach g groups
        (if (KG-FindDef model (KG-MakeName base newiter (car g)))
          (setq toexist (cons (car g) toexist))
          (setq tocreate (cons (car g) tocreate))
        )
      )
      (setq torename (KG-ConflictCandidates model base))
      (setq out
        (list
          (cons "family" base)
          (cons "newiter" newiter)
          (cons "master" mastername)
          (cons "scan" scan)
          (cons "variants-to-create" (reverse tocreate))
          (cons "variants-existing" (reverse toexist))
          (cons "nested-to-update" (cdr (assoc "to-update" nested)))
          (cons "nested-to-add" (cdr (assoc "to-add" nested)))
          (cons "nested-all" newnested)
          (cons "pre-rename" torename)
          (cons "instances" (KG-FindOldIterations model base newiter))
          (cons "warnings" nil)
        ))
      (if (null (KG-FindDef model mastername))
        (setq out (KG-SetAssoc "warnings"
                       (cons (strcat "Определение мастер-версии \""
                                     mastername "\" не найдено в файле.")
                             (cdr (assoc "warnings" out)))
                       out))
      )
      out
    )
  )
)

;;;===========================================================================
;;; РАЗДЕЛ 5. ВАЛИДАЦИЯ И ОТЧЁТНОСТЬ (Этап 12)
;;;===========================================================================

(defun KG-ValidateIntegration (model base newiter expected-groups / pairs left
                                     newpairs newservice out lost per v exp got
                                     defnm)
  (setq pairs
    (if (/= (KG-IterToStr newiter) "")
      (KG-FindOldIterations model base newiter)
      (vl-remove-if-not
        '(lambda (pr)
           (or (/= (nth 1 (cdr pr)) "")
               (KG-IsTempDefName (KG-CdrCI "def" (car pr)))
               (KG-IsTempDefName (KG-CdrCI "eff" (car pr)))))
        (KG-FindFamilyInstances model base))
    )
  )
  (setq left (length pairs))
  (setq newpairs nil)
  (foreach ins (KG-ModelInsts model)
    (if (and (KG-IsIntegrationName (KG-CdrCI "eff" ins) base newiter)
             (not (KG-IsTempDefName (KG-CdrCI "eff" ins)))
             (not (KG-IsTempDefName (KG-CdrCI "def" ins))))
      (setq newpairs (cons (cons ins (KG-ParseBlockName (KG-CdrCI "eff" ins)))
                           newpairs))
    )
  )
  ;; Служебные суффиксы ($0$, $1$, _new, «копия») ищутся только в именах,
  ;; которые занимает НАША замена. Анонимные определения AutoCAD
  ;; (*Model_Space, *Paper_Space, *U8, *D3 ...) проверять нельзя: они есть
  ;; в любом чертеже и к результату интеграции отношения не имеют --
  ;; на реальном чертеже этот список давал 79 ложных «служебных имён».
  (setq newservice nil)
  (foreach pr newpairs
    (setq defnm (KG-CdrCI "def" (car pr)))
    (if (and defnm
             (not (KG-IsAnonymousName defnm))
             (KG-IsServiceName defnm)
             (not (member defnm newservice)))
      (setq newservice (cons defnm newservice))
    )
  )
  (setq per nil lost 0)
  (foreach g (KG-ExpectedWithExisting expected-groups KG-ALREADYNEW)
    (setq v (car g))
    (setq exp (cdr g))
    (setq got (length (vl-remove-if-not
                        '(lambda (pr) (KG-StrEq (nth 2 (cdr pr)) v))
                        newpairs)))
    (if (/= exp got) (setq lost (+ lost (abs (- exp got)))))
    (setq per (cons (list v exp got (= exp got)) per))
  )
  (list
    (cons "old-left" left)
    (cons "new-total" (length newpairs))
    (cons "per-variant" (reverse per))
    (cons "service-names" (reverse newservice))
    (cons "lost" lost)
    (cons "ok" (and (= left 0) (= lost 0)))
  )
)

;; Ожидаемое число экземпляров по вариантам с учётом тех, что УЖЕ были
;; на новой итерации до замены. Без этой поправки отчёт сравнивает
;; фактическое число со счётчиком только СТАРЫХ экземпляров: лишний блок
;; новой версии (например, копия, оставшаяся от диагностической вставки)
;; даёт ложное «РАСХОЖДЕНИЕ» и ложную потерю.
;; groups = ((вариант . список-экземпляров) ...), already = ((вариант . n) ...)
(defun KG-ExpectedWithExisting (groups already / out v hit)
  (setq out nil)
  (foreach g groups
    (setq v (car g))
    (setq hit (KG-AssocCI v already))
    (setq out (cons (cons v (+ (length (cdr g)) (if hit (cdr hit) 0))) out))
  )
  (foreach a already
    (if (not (KG-AssocCI (car a) groups))
      (setq out (cons (cons (car a) (cdr a)) out))
    )
  )
  (reverse out)
)

;; Семейство, к которому относился отчёт.
(defun KG-ReportBase (rep) (KG-AsString (cdr (assoc "base" rep))))


;; Диагноз «экземпляры есть, а план пуст».
;;
;; Прогон сборки 52: строка «Экземпляров семейства в чертеже: 2» с чистыми
;; именами «Комплект КП50 v1.1» и «Комплект КП50 v1.2 КП45387» -- и тут же
;; «Заменено экземпляров: 0», «Создано вариантов: 0». Значит, вставка
;; находится одним путём (ssget + эффективное имя через COM) и НЕ
;; находится другим (модель, по которой строится план). Два этих числа и
;; есть диагноз: если они расходятся, дело не в именах и не в плане, а в
;; чтении модели. Возвращает текст строки отчёта.
(defun KG-ModelScanLine (base)
  (strcat "Экземпляров по модели (по ним строится план): "
          (KG-NumStr (length (KG-Safe '(lambda ()
                                         (KG-FindFamilyInstances
                                           (KG_DBGetModel) base))
                                      nil)))
          ", по вставкам напрямую: "
          (KG-NumStr (KG-AsNum
                       (car (KG-Safe '(lambda () (KG-FamilyInstances base))
                                     (list -1 nil)))
                       -1)))
)

;; Итоговый отчёт интеграции (п. 16 ТЗ)
(defun KG-PrintIntegrationReport (rep / plan val created replaced v s
                                      nerr nwarn bad)
  (setq plan (cdr (assoc "plan" rep)))
  (setq val (cdr (assoc "validation" rep)))
  (setq created (cdr (assoc "created" rep)))
  (setq replaced (cdr (assoc "replaced" rep)))

  ;; 72.7. Весь отчёт складывается в буфер: после прогона его можно
  ;; получить командой RDBREPORT, не вылавливая строки в журнале.
  (setq KG-REPORT-CAPTURE t)
  (setq KG-REPORT-BUF nil)

  (if created
    (progn
      (KG-Say (strcat "Созданы определения вариантов: " (KG-NumStr (length created))))
      (KG-SayList created 5)
    )
  )
  (if (cdr (assoc "nested-to-update" plan))
    (progn
      (KG-Say (strcat "Вложенных определений обновлено: "
                      (KG-NumStr
                        (- (length (cdr (assoc "nested-to-update" plan)))
                           (length (cdr (assoc "nested-stale" rep)))))))
      (if (and KG-TRACE (cdr (assoc "nested-to-update" plan)))
        (KG-SayList (cdr (assoc "nested-to-update" plan)) 5)
      )
    )
  )
  (if (cdr (assoc "nested-stale" rep))
    (progn
      (KG-Say (strcat "ОСТАЛИСЬ СТАРЫМИ: "
                      (KG-NumStr (length (cdr (assoc "nested-stale" rep))))))
      (foreach v (cdr (assoc "nested-stale" rep))
        (KG-Say (strcat "  " v "   [ОСТАЛОСЬ СТАРЫМ]")))
    )
  )
  (if (cdr (assoc "nested-to-add" plan))
    (progn
      (KG-Say (strcat "Добавлены новые вложенные определения: "
                      (KG-NumStr (length (cdr (assoc "nested-to-add" plan))))))
      (KG-SayList (cdr (assoc "nested-to-add" plan)) 5)
    )
  )

  (if KG-TRACE
    (progn
      (KG-SayKV "Кандидатов на освобождение" (KG-NumStr (cdr (assoc "candidates" rep))))
      (KG-SayKV "Освобождено имён до вставки" (KG-NumStr (cdr (assoc "freed" rep))))
      (KG-SayKV "Из них занято пришедшими" (KG-NumStr (length (cdr (assoc "renames" rep)))))
      (KG-SayKV "Пришло определений из буфера" (KG-NumStr (length (cdr (assoc "arrived" rep)))))
    )
  )
  (if (cdr (assoc "rename-failed" rep))
    (progn
      (KG-SayKV "Не удалось переименовать"
                (KG-NumStr (length (cdr (assoc "rename-failed" rep)))))
      (KG-Say (strcat "  " (KG-JoinNames (cdr (assoc "rename-failed" rep)))))
    )
  )

  (KG-SayKV "Мастер-версия" (KG-AsString KG-MASTER-STATE))
  (if (and KG-MASTER-STATE (KG-StrContains KG-MASTER-STATE "ОСТАЛАСЬ СТАРОЙ"))
    (KG-Say (strcat "ВНИМАНИЕ: определение мастер-версии НЕ обновилось -- "
                    "интеграция шла от устаревшего мастера."))
  )

  (KG-Say "=== Результат ===")
  (setq bad (KG-Safe '(lambda ()
                        (KG-FamilyInstances (KG-ReportBase rep)))
                     (list -1 nil)))
  (if (>= (KG-AsNum (car bad) 0) 0)
    (progn
      (KG-SayKV "Экземпляров семейства в чертеже" (KG-NumStr (car bad)))
      (if (and KG-TRACE (car (cdr bad)))
        (progn
          (KG-Say "  какими именами видны:")
          (foreach v (car (cdr bad)) (KG-Say (strcat "    " (KG-AsString v))))
        )
      )
    )
  )
  (KG-SayKV "Заменено экземпляров" (KG-NumStr (cdr (assoc "replaced" replaced))))
  (if (> (KG-AsNum (cdr (assoc "space-unknown" replaced)) 0) 0)
    (KG-SayKV "Не заменено (внутри определений блоков)"
              (KG-NumStr (cdr (assoc "space-unknown" replaced))))
  )
  (KG-SayKV "Создано вариантов" (KG-NumStr (length created)))
  (if (cdr (assoc "plan" rep))
    (progn
      (KG-SayKV "Снято старых определений семейства"
                (KG-NumStr (length (cdr (assoc "retired" rep)))))
      (if (and KG-TRACE (cdr (assoc "retired" rep)))
        (KG-SayList (cdr (assoc "retired" rep)) 8)
      )
    )
  )
  (if (cdr (assoc "retire-left" rep))
    (progn
      (KG-SayKV "ОСТАЛОСЬ старых определений (есть ссылки)"
                (KG-NumStr (length (cdr (assoc "retire-left" rep)))))
      (KG-SayList (cdr (assoc "retire-left" rep)) 8)
    )
  )
  (KG-SayKV "Обновлено вложенных определений"
            (KG-NumStr (- (length (cdr (assoc "nested-to-update" plan)))
                          (length (cdr (assoc "nested-stale" rep))))))
  (if (cdr (assoc "nested-stale" rep))
    (KG-SayKV "Из них остались старыми"
              (KG-NumStr (length (cdr (assoc "nested-stale" rep))))))
  (if (> (KG-AsNum (cdr (assoc "rewired" rep)) 0) 0)
    (KG-SayKV "Перепривязано ссылок на прежние имена"
              (KG-NumStr (KG-AsNum (cdr (assoc "rewired" rep)) 0)))
  )
  (if (> (KG-AsNum (nth 0 (cdr (assoc "vis-nested-restored" rep))) 0) 0)
    (progn
      (KG-SayKV "Возвращено состояний вложенных блоков"
                (KG-NumStr (KG-AsNum (nth 0 (cdr (assoc "vis-nested-restored" rep))) 0)))
      (if (nth 5 (cdr (assoc "vis-nested-restored" rep)))
        (progn
          (KG-Say "  определения:")
          (KG-SayList (nth 5 (cdr (assoc "vis-nested-restored" rep))) 5)
        )
      )
    )
  )
  (if (> (KG-AsNum (nth 2 (cdr (assoc "vis-nested-restored" rep))) 0) 0)
    (KG-SayKV "  из них записать не удалось"
              (KG-NumStr (nth 2 (cdr (assoc "vis-nested-restored" rep))))))
  (if (> (KG-AsNum (nth 3 (cdr (assoc "vis-nested-restored" rep))) 0) 0)
    (KG-SayKV "  из них запись не подтвердилась"
              (KG-NumStr (nth 3 (cdr (assoc "vis-nested-restored" rep))))))

  (KG-SayKV "Восстановлено состояний видимости"
            (KG-NumStr (cdr (assoc "vis-restored" replaced))))
  (KG-SayKV "Прочитано состояний вложенных блоков"
            (KG-NumStr (cdr (assoc "nested-vis-n" replaced))))
  (if (cdr (assoc "nested-from-u" replaced))
    (KG-SayKV "  из них у представлений экземпляров (*U)"
              (KG-NumStr (cdr (assoc "nested-from-u" replaced)))))
  (if (cdr (assoc "nested-from-def" replaced))
    (KG-SayKV "  из них состояний по умолчанию из определения"
              (KG-NumStr (cdr (assoc "nested-from-def" replaced)))))
  (if (cdr (assoc "vis-notfound" replaced))
    (KG-SayKV "Вложенных блоков не найдено в новой версии"
              (KG-NumStr (cdr (assoc "vis-notfound" replaced)))))
  (KG-SayKV "Экземпляров без анонимного представления"
            (KG-NumStr (cdr (assoc "vis-noanon" replaced))))
  (if (and (> (KG-AsNum (cdr (assoc "replaced" replaced)) 0) 0)
           (< (KG-AsNum (cdr (assoc "nested-vis-n" replaced)) 0) 1))
    (KG-Say (strcat "ВНИМАНИЕ: у заменённых экземпляров не прочитано ни "
                    "одного состояния вложенных блоков."))
  )
  (if (> (KG-AsNum (cdr (assoc "vis-missing" replaced)) 0) 0)
    (KG-SayKV "  состояний не найдено в новой версии"
              (KG-NumStr (cdr (assoc "vis-missing" replaced)))))
  (if (> (KG-AsNum (cdr (assoc "dyn-restored" replaced)) 0) 0)
    (KG-SayKV "Перенесено динамических свойств"
              (KG-NumStr (cdr (assoc "dyn-restored" replaced)))))

  (KG-SayKV "Старых экземпляров осталось" (KG-NumStr (cdr (assoc "old-left" val))))
  (KG-SayKV "Новых экземпляров" (KG-NumStr (cdr (assoc "new-total" val))))
  (KG-SayKV "Потерь экземпляров" (KG-NumStr (cdr (assoc "lost" val))))
  (KG-SayKV "Предупреждений" (KG-NumStr (length (cdr (assoc "warnings" rep)))))
  (KG-SayKV "Ошибок" (KG-NumStr (length (cdr (assoc "errors" rep)))))
  (if KG-DYN-FAIL
    (progn
      (KG-Say "Динамические свойства, которые не удалось перенести:")
      (foreach x (reverse KG-DYN-FAIL)
        (KG-Say (strcat "  handle " (nth 0 x) ", «" (nth 1 x) "» = "
                        (nth 2 x) " (" (nth 3 x) ")")))
    )
  )

  (foreach s (cdr (assoc "per-variant" val))
    (KG-Say (strcat "  Вариант " (KG-VarLabel (nth 0 s)) ": ожидалось "
                    (KG-NumStr (nth 1 s)) ", стало " (KG-NumStr (nth 2 s))
                    (if (nth 3 s) "  [OK]" "  [РАСХОЖДЕНИЕ]")))
  )
  (foreach w (cdr (assoc "warnings" rep))
    (KG-Say (strcat "ВНИМАНИЕ:\n" w))
  )
  (foreach s (cdr (assoc "errors" rep))
    (KG-Say (strcat "ОШИБКА: " s))
  )
  (if (cdr (assoc "service-names" val))
    (progn
      (KG-Say "ВНИМАНИЕ: у созданных экземпляров служебные суффиксы в именах:")
      (foreach s (cdr (assoc "service-names" val))
        (KG-Say (strcat "  " s)))
    )
  )

  ;; Итог одной строкой. Отчёт длинный, и по нему не сразу видно,
  ;; состоялся прогон или нет: нули ошибок и предупреждений теряются
  ;; среди счётчиков. Расхождение по варианту считается ошибкой -- это
  ;; нарушение п. «количество экземпляров сохраняется».
  (setq nerr (length (cdr (assoc "errors" rep))))
  (setq nwarn (+ (length (cdr (assoc "warnings" rep)))
                 (KG-AsNum (cdr (assoc "lost" val)) 0)
                 (KG-AsNum (cdr (assoc "old-left" val)) 0)))
  (setq bad nil)
  (foreach v (cdr (assoc "per-variant" val))
    (if (not (nth 3 v)) (setq bad (1+ (if bad bad 0))))
  )
  (KG-Say (strcat "=== ИТОГ: "
                  (cond
                   ((> nerr 0)
                    (strcat "ОШИБКИ (" (itoa nerr) ") -- см. строки выше"))
                   ((> (if bad bad 0) 0)
                    (strcat "РАСХОЖДЕНИЕ ПО КОЛИЧЕСТВУ (" (itoa bad) ")"))
                   ((> nwarn 0)
                    (strcat "выполнено, есть предупреждения ("
                            (itoa nwarn) ")"))
                    (t "УСПЕШНО, замечаний нет"))
                  " ==="))

  ;; 72.7. Сохраняем отчёт по семейству для RDBREPORT. Последний отчёт
  ;; остаётся в KG-REPORT-LAST, все семейства -- в KG-REPORT-ALL.
  (setq KG-REPORT-LAST (reverse KG-REPORT-BUF))
  (setq KG-REPORT-ALL
    (append KG-REPORT-ALL
            (list (cons (KG-ReportBase rep) KG-REPORT-LAST))))
  (setq KG-REPORT-CAPTURE nil)
  (setq KG-DYN-FAIL nil)
)


;; Добить строку пробелами до нужной ширины. В AutoCAD НЕТ функции
;; make-string -- на реальном чертеже это дало бы
;; "no function definition: MAKE-STRING".
(defun KG-Pad (s width / out)
  (setq out (KG-AsString s))
  (while (< (strlen out) width) (setq out (strcat out " ")))
  out
)

(defun KG-PrintScanReport (scan / g)
  (KG-Say "Найдены старые варианты:")
  (foreach g (cdr (assoc "groups" scan))
    (princ (strcat "\nВариант " (KG-VarLabel (car g))
                   (KG-Pad "" (max 0 (- 10 (strlen (if (car g) (car g) "")))))
                   ": " (itoa (length (cdr g)))))
  )
  (KG-SayKV "Всего" (KG-NumStr (cdr (assoc "total" scan))))
)

(defun KG-PrintSpaceReport (scan)
  (KG-Say "Пространства:")
  (foreach s (cdr (assoc "spaces" scan))
    (princ (strcat "\n  " (KG-AsString (car s)) " : " (KG-NumStr (cdr s))))
  )
)

;;;===========================================================================
;;; РАЗДЕЛ 6. КОНТРАКТ АДАПТЕРА БД
;;;
;;; Чтение:
;;;   KG_DBGetModel          ()                 -> модель чертежа
;;;
;;; Исполнение (все должны возвращать nil при неудаче, а не ронять команду):
;;;   KG_EXAllDefNames       ()                 -> имена определений
;;;   KG_EXDefExists         (name)             -> T/nil
;;;   KG_EXRenameDef         (old new)          -> T/nil
;;;   KG_EXDeleteDef         (name)             -> T/nil
;;;   KG_EXPasteAtOrigin     ()                 -> T/nil   техническая вставка
;;;   KG_SnapshotDrawing     ()                 -> снимок handle'ов вхождений
;;;   KG_EXNewInstancesSince (snapshot)         -> новые handle'ы
;;;   KG_EXInstanceHandle    (handle)           -> модель экземпляра | nil
;;;   KG_EXCreateInstance    (defname instmodel)-> handle | nil
;;;   KG_EXSetEffectiveName  (handle defname)   -> T/nil
;;;   KG_EXDeleteInstance    (handle)           -> T/nil
;;;   KG_EXRestoreDynProps   (handle dynprops)  -> число восстановленных
;;;   KG_EXSetNestedVisibility (handle nm value)-> T/nil
;;;   KG_EXCreateDefFromMaster (newname master) -> T/nil
;;;
;;;   KG-RefreshSpaceMap     ()                 -> перестроить карту
;;;       handle -> пространство. Нужна после вставки: карта, построенная
;;;       до вставки, не знает о новых объектах.
;;;===========================================================================

;;;===========================================================================
;;; РАЗДЕЛ 7. ШАГИ ИНТЕГРАЦИИ И ОРКЕСТРАЦИЯ
;;;===========================================================================

;; Имя, под которым сохраняется старое определение после перевода ссылок
;; на новое. Начинается с «~»: в списке блоков и в окне PURGE мусор
;; прошлых интеграций собирается подряд, отдельно от рабочих имён.
;; Итерация, если она есть, отделяется вторым «~» -- видно, какой итерации
;; предшествовало определение. Служебных маркеров вроде $0$, _new,
;; "копия" (п. 20 ТЗ) в имени нет; «$N$» добавляет только KG-UniqueName,
;; если имя уже занято.
;; Определение, пришедшее из внешней ссылки: имя вида "чертёж|блок".
;; Переименовывать такие нельзя -- на реальном чертеже с 264 кандидатами
;; попытка дала 0xC0000005. Флаг is-xref у них не выставлен: ссылка --
;; сам внешний файл, а это его зависимое определение.
(defun KG-IsXrefDepName (nm)
  (KG-StrContains (KG-AsString nm) "|")
)

(defun KG-TempDefName (base iter used / is)
  (setq is (KG-IterToStr iter))
  (KG-UniqueName
    (strcat "~" (KG-AsString base)
            (if (/= is "") (strcat "~" is) ""))
    used)
)

;; Шаг 1. Освободить имена ДО вставки из буфера.
;; Возвращает список троек (исходное-имя временное-имя определение-источник).
(defun KG-Step_PreRename (names iter base model / used out tmp nm kg-t0 kg-src kg-pairs)
  ;; Список занятых имён читается ОДИН раз. Раньше он перечитывался в
  ;; каждой итерации: на чертеже с 264 кандидатами это 264 полных прохода
  ;; по таблице блоков. Меняется список только нашими же
  ;; переименованиями, поэтому новое имя достаточно в него добавить.
  (setq used (KG-Safe '(lambda () (KG_EXAllDefNames)) nil))
  ;; 71.6: карта «вложенное -> кто вкладывает» строится ОДИН раз на весь
  ;; список имён (см. KG-NestedPairs). Освобождение имён 71.5 стоило
  ;; 5.09 с, и почти всё это -- повторные обходы одних и тех же
  ;; определений на каждое имя.
  (setq kg-t0 (KG-SubT0))
  (setq kg-pairs (KG-Safe '(lambda () (KG-NestedPairs model)) nil))
  (KG-SubT1 "пре: карта вложений (построение)" kg-t0)
  (setq out nil)
  (foreach nm names
    (if (KG-IsSystemBlockName nm)
      (princ (strcat "\nПропущено, системное определение или из внешней ссылки: \""
                     nm "\""))
      (progn
        (setq kg-t0 (KG-SubT0))
        (if (KG_EXDefExists nm)
          (progn
            (KG-SubT1 "пре: проверка имени" kg-t0)
            ;; Метка на каждое имя: если переименование уронит AutoCAD,
            ;; последняя назовёт виновника. Печатается только на подробном
            ;; уровне -- имён больше сотни, и KG-LAST-STEP запоминается
            ;; в любом случае.
            (KG-TraceDetail (strcat "переименование \"" nm "\""))
            (setq kg-t0 (KG-SubT0))
            (setq tmp (KG-TempDefName nm iter used))
            (KG-SubT1 "пре: подбор временного имени" kg-t0)
            (setq kg-t0 (KG-SubT0))
            (if (KG_EXRenameDef nm tmp)
              (progn
                (KG-SubT1 "пре: переименование" kg-t0)
                (setq used (cons tmp used))
                (setq kg-t0 (KG-SubT0))
                (setq kg-src (KG-SourceOfNestedIn kg-pairs base nm))
                (KG-SubT1 "пре: определение-источник" kg-t0)
                (setq out (cons (list nm tmp kg-src) out))
              )
              (progn
                (KG-SubT1 "пре: переименование" kg-t0)
                (setq KG-PRENAME-FAILED (cons nm KG-PRENAME-FAILED))
                (princ (strcat "\nВНИМАНИЕ: не удалось временно переименовать \""
                               nm "\" -- новое определение с этим именем"
                               " не придёт."))
              )
            )
          )
        )
      )
    )
  )
  (reverse out)
)

;; Из переименованных имён оставить только те, что буфер реально принёс.
;; Остальные возвращаются на место: освобождать имя имеет смысл только
;; тогда, когда на него что-то пришло. Иначе определение, которого в
;; новом мастере нет (п. 8.4 ТЗ: не удалять), осталось бы под служебным
;; именем «~имя», а итоговые имена обязаны быть чистыми.
(defun KG-Step_RollbackNotArrived (renames arrived / out)
  (setq out nil)
  (foreach r renames
    (if (KG-StrInterCI (list (nth 0 r)) arrived)
      (setq out (cons r out))
      (KG_EXRenameDef (nth 1 r) (nth 0 r))
    )
  )
  (reverse out)
)

;; Откат временных переименований (когда буфер не «пришёл»)
(defun KG-Step_RollbackRename (renames / out)
  (setq out nil)
  (foreach r renames
    (if (KG_EXRenameDef (nth 1 r) (nth 0 r))
      (setq out (cons (nth 0 r) out))
    )
  )
  (if out
    (princ (strcat "\nПереименования откатаны, чертёж не изменён: "
                   (KG-JoinNames out)))
  )
  (reverse out)
)

;; Что реально пришло из буфера
(defun KG-Step_DetectArrived (beforedefs afterdefs)
  (KG-StrDiffCI afterdefs beforedefs)
)

;; Найти имя мастер-версии среди пришедших определений
(defun KG-DetectMasterName (newdefs / p vnames parennames plainnames mdl nested-all roots nm c)
  (setq vnames nil parennames nil plainnames nil)
  (foreach nm newdefs
    (if (and (not (KG-IsAnonymousName nm))
             (not (KG-IsSystemBlockName nm))
             (not (KG-IsTempDefName nm)))
      (progn
        (if (and (setq p (KG-ParseVName nm)) (= (nth 2 p) ""))
          (setq vnames (cons nm vnames))
        )
        (if (and (setq p (KG-ParseParenName nm)) (= (nth 2 p) ""))
          (setq parennames (cons nm parennames))
        )
        (setq plainnames (cons nm plainnames))
      )
    )
  )
  (cond
    (vnames (car (reverse vnames)))
    (parennames (car (reverse parennames)))
    (plainnames
     ;; Исключаем вложенные детали: мастер -- это корневой блок
     (setq mdl (KG-ReadModelNoProps))
     (setq nested-all nil)
     (if mdl
       (foreach nm plainnames
         (foreach c (KG-GetNestedBlocks mdl nm)
           (if (not (member (KG-StrKey c) nested-all))
             (setq nested-all (cons (KG-StrKey c) nested-all))
           )
         )
       )
     )
     (setq roots
       (vl-remove-if '(lambda (x) (member (KG-StrKey x) nested-all))
                     (reverse plainnames)))
     (if roots (car roots) (car (reverse plainnames)))
    )
    (t nil)
  )
)

;; Из новых экземпляров выбрать мастер-версию (имя без суффикса)
(defun KG-PickMasterHandle (handles / best m p)
  (setq best nil)
  (foreach h handles
    (if (not best)
      (progn
        (setq m (KG_EXInstanceHandle h))
        (if m
          (progn
            (setq p (KG-ParseBlockName (KG-CdrCI "eff" m)))
            (if (and p (= (nth 2 p) "")) (setq best h))
          )
        )
      )
    )
  )
  (if (and (null best) handles)
    (setq best (car handles))
  )
  best
)

;; 71.3. Все мастер-версии, пришедшие из буфера: одна запись на семью --
;; (имя base итерация). Мастер -- версионное имя без варианта («БАЗА
;; v1.52»), итерация с точкой (схема заказчика «vN.N»). Вложенные
;; определения мастерами не считаются: «Опора v2.1» внутри пришедшего
;; комплекта -- не семья чертежа. Прежний KG-DetectMasterName остаётся
;; запасным путём: он же обслуживает безверсионную подмену.
(defun KG-DetectMasterFamilies (newdefs model / out nm p base hit nestedall)
  (setq out nil)
  (foreach nm newdefs
    (if (and (not (KG-IsAnonymousName nm))
             (not (KG-IsSystemBlockName nm))
             (not (KG-IsTempDefName nm)))
      (progn
        (setq p (KG-ParseVName nm))
        (if (and p (= (nth 2 p) "") (/= (KG-IterToStr (nth 1 p)) "")
                 (KG-StrContains (KG-IterToStr (nth 1 p)) "."))
          (progn
            (setq base (nth 0 p))
            (setq hit (KG-AssocCI base out))
            (if (not hit)
              (setq out (cons (cons base (list nm base (nth 1 p))) out))
              (if (KG-IterOlder (nth 2 (cdr hit)) (nth 1 p))
                (setq out (KG-SetAssoc base (list nm base (nth 1 p)) out))
              )
            )
          )
        )
      )
    )
  )
  (setq out (reverse out))
  (if (and model out)
    (progn
      (setq nestedall nil)
      (foreach c out
        (foreach c2 (KG-GetNestedBlocks model (nth 0 (cdr c)))
          (if (not (KG-StrInterCI (list c2) nestedall))
            (setq nestedall (cons c2 nestedall))
          )
        )
      )
      (setq out
        (vl-remove-if '(lambda (c)
                         (KG-StrInterCI (list (nth 0 (cdr c))) nestedall))
                      out))
    )
  )
  (mapcar 'cdr out)
)

;; Экземпляр-«кирпич» новой мастер-версии из вставки буфера: его
;; эффективное имя равно имени мастера. nil -- вставки не было.
(defun KG-FindNewMasterInstance (snap mastername / best h m)
  (setq best nil)
  (foreach h (KG-Safe '(lambda () (KG_EXNewInstancesSince snap)) nil)
    (if (not best)
      (progn
        (setq m (KG_EXInstanceHandle h))
        (if (and m (KG-StrEq (KG-CdrCI "eff" m) mastername))
          (setq best h)
        )
      )
    )
  )
  best
)

;; Шаг 2. Создать недостающие варианты из мастер-версии (Этап 9)
;;; Вариант создаётся глубоким клонированием, чтобы он остался
;;; ДИНАМИЧЕСКИМ, как мастер-версия. Если ObjectDBX недоступен --
;;; запасной путь без динамики, с явным предупреждением.
(defun KG_EXCreateDefFromMaster (newname mastername / ok cur curdyn srcdyn)
  (setq cur (KG_EXDefExists newname))
  ;; Определение уже есть. Если мастер-версия динамическая, а оно нет --
  ;; это остаток прошлой попытки, когда вариант строился копированием
  ;; объектов. Такое определение пересоздаётся, иначе оно навсегда
  ;; останется статическим.
  (if cur
    (progn
      (setq curdyn (KG-Safe '(lambda () (KG-EXDefIsDynamic newname)) nil))
      (setq srcdyn (KG-Safe '(lambda () (KG-EXDefIsDynamic mastername)) nil))
      (if (and srcdyn (not curdyn))
        (progn
          (princ (strcat "\nВНИМАНИЕ: \"" newname "\" уже есть и оно "
                         "статическое -- пересоздаю динамическим."))
          (if (KG-Safe '(lambda () (KG_EXDeleteDef newname)) nil)
            (setq cur nil)
            (princ (strcat "\nВНИМАНИЕ: \"" newname "\" используется "
                           "экземплярами, удалить нельзя -- оно останется "
                           "статическим. Удалите его экземпляры и повторите."))
          )
        )
      )
    )
  )
  (if cur
    t
    (progn
      ;; Обёртка ОБЯЗАНА записывать причину: KG-Safe проглатывал исключение
      ;; из KG_EXCopyDefDeep, KG-DBX-ERR оставался пустым, и отчёт печатал
      ;; бесполезное «скопировать определение не удалось».
      (setq ok
        (KG-DBX-Try
          (strcat "глубокое копирование \"" (KG-AsString mastername)
                  "\" -> \"" (KG-AsString newname) "\"")
          '(lambda () (KG_EXCopyDefDeep mastername newname))))
      (if (not ok)
        (progn
          (princ (strcat "\nВНИМАНИЕ: вариант \"" newname "\" создан БЕЗ "
                         "динамических свойств -- он будет статическим блоком."
                         "\nПричина: "
                         (if KG-DBX-ERR
                           (KG-JoinNames (reverse KG-DBX-ERR))
                           "не сообщена (KG_EXCopyDefDeep вернула nil, ни один шаг не отказал)")
                         "\nПроверьте подробнее командой INTDBXTEST."))
          (setq ok (KG-EXCreateDefStatic newname mastername))
        )
      )
      ok
    )
  )
)

(defun KG-Step_CreateVariants (plan / base newiter out nm st)
  (setq base (cdr (assoc "family" plan)))
  (setq newiter (cdr (assoc "newiter" plan)))
  (setq out nil)
  (foreach v (cdr (assoc "variants-to-create" plan))
    (setq nm (KG-MakeName base newiter v))
    (if (KG_EXCreateDefFromMaster nm (cdr (assoc "master" plan)))
      (progn
        (setq out (cons nm out))
        ;; Устанавливаем состояния вложенных динамических блоков в определение варианта
        (if (and (/= (KG-AsString v) "") (KG_EXDefExists nm))
          (progn
            (setq st (KG-FindVariantNestedStates base v plan))
            (if st
              (KG-Safe '(lambda () (KG-RestoreNestedVisOne nm st)) nil)
            )
          )
        )
      )
      (princ (strcat "\nОШИБКА: невозможно создать вариант \"" nm "\"."))
    )
  )
  (reverse out)
)

;; Шаг 3. Заменить старые экземпляры (Этап 10) и восстановить видимости
;; (Этап 11). Экземпляр пересоздаётся, поэтому его Handle меняется --
;; это отражается в отчёте (п. 15 ТЗ).
(defun KG-Step_ReplaceInstances (model plan oldpairs / base newiter nh tgt
                                       plan-vis old restored missing warns
                                       out cnt nospace pr inst v pn pstate
                                       phit pwarn doone dynrestored dynread
                                       nvread notfound noanon retry pv r
                                       nfromu nfromdef src nv kg-t0 gcnt)
  (setq base (cdr (assoc "family" plan)))
  (setq newiter (cdr (assoc "newiter" plan)))
  (setq restored 0 missing 0 warns nil out nil cnt 0 nospace 0
        dynrestored 0 dynread 0 nvread 0 notfound 0 noanon 0
        nfromu 0 nfromdef 0 gcnt 0)
  (foreach pr oldpairs
    (setq inst (car pr))
    ;; Экземпляр без определённого пространства (лежит внутри определения
    ;; блока) пересоздавать нельзя: нельзя гарантировать, что он останется
    ;; на месте. Он остаётся как есть, вложенные определения в нём
    ;; обновятся сами, потому что определения переименовываются глобально.
    (setq doone (KG-CdrCI "space" inst))
    (if (not doone)
      (progn
        (setq nospace (1+ nospace))
        (princ (strcat "\nВНИМАНИЕ: экземпляр \""
                       (KG-AsString (KG-CdrCI "eff" inst))
                       "\" (handle " (KG-AsString (KG-CdrCI "handle" inst))
                       ") лежит внутри определения блока и не заменён."))
      )
    )
    (setq v (nth 2 (cdr pr)))
    (setq tgt (KG-MakeName base newiter v))
    ;; 72. Фазы замены -- под суб-замер: на крупном чертеже шаг стоил
    ;; 86 с на три экземпляра, и не видно, что из него дороже.
    (setq kg-t0 (KG-SubT0))
    (setq plan-vis (KG-PlanNestedVisibility model inst tgt))
    (KG-SubT1 "замена: план видимости" kg-t0)
    (setq old (KG-CdrCI "handle" inst))
    (setq kg-t0 (KG-SubT0))
    (setq nh (if doone (KG_EXCreateInstance tgt inst) nil))
    (KG-SubT1 "замена: создание экземпляра" kg-t0)
    (if (and doone nh)
      (progn
        ;; Свойства самого блока (его собственный параметр видимости)
        ;; восстанавливаются отдельно от состояний вложенных блоков.
        ;; Счётчик раньше выбрасывался, и отчёт печатал «восстановлено 0»,
        ;; хотя состояние мастера было перенесено.
        ;; ВАЖНО: вызов ПРЯМОЙ, без KG-Safe. На реальном чертеже
        ;; (KG-Safe (lambda () ...) ...) падает с «неверная функция:
        ;; #<SUBR ... -lambda->»: vl-catch-all-apply принимает имя функции
        ;; или КВОТИРОВАННУЮ лямбду, а вычисленная лямбда становится
        ;; SUBR'ом. Квотированная здесь не годится -- в стенде она не видит
        ;; локальных nh и inst. Сама KG_EXRestoreDynProps внутри полностью
        ;; под перехватом, поэтому обёртка ей не нужна.
        ;; Два счётчика вместо одного: по одному нулю нельзя отличить
        ;; «у старых экземпляров нечего было читать» от «прочитали, но
        ;; записать в новый экземпляр не удалось».
        (setq kg-t0 (KG-SubT0))
        (setq dynread
          (+ dynread (length (KG-CdrCI "dyn-props" inst))))
        (setq dynrestored
          (+ dynrestored
             (KG-AsNum
               (KG_EXRestoreDynProps nh (KG-CdrCI "dyn-props" inst)) 0)))
        (KG-SubT1 "замена: динамические свойства" kg-t0)
        ;; Прибавляется ЧИСЛО СОСТОЯНИЙ, а не единица за экземпляр:
        ;; источник («*U» или «ОПРЕДЕЛЕНИЕ») один на экземпляр, а
        ;; состояний у него может быть несколько. В сборке 39 отчёт
        ;; печатал «прочитано состояний 6», а ниже «из них у
        ;; представлений 1 / из определения 1», и 6 не сходилось с 1+1.
        (setq nv (KG-AsNum (KG-CdrCI "nested-vis-n" inst) 0))
        (setq nvread (+ nvread nv))
        (setq src (KG-CdrCI "nested-vis-src" inst))
        (cond
          ((KG-StrEq src "*U") (setq nfromu (+ nfromu nv)))
          ((KG-StrEq src "ОПРЕДЕЛЕНИЕ") (setq nfromdef (+ nfromdef nv))))
        ;; Первый проход. «НЕ НАЙДЕН» не приговор: установка состояния
        ;; одного вложенного блока пересоздаёт анонимное представление
        ;; экземпляра, и следующая вставка ищется уже в новом. Такие пары
        ;; уходят во второй проход.
        (setq kg-t0 (KG-SubT0))
        (setq retry nil)
        (foreach pv plan-vis
          (setq pn (car pv))
          (setq pstate (nth 0 (cdr pv)))
          (setq phit (nth 1 (cdr pv)))
          (setq pwarn (nth 2 (cdr pv)))
          (setq r (KG_EXSetNestedVisibility nh pn pstate))
          (cond
            ;; успех: KG_EXSetNestedVisibility возвращает именно T.
            ;; Счётчики различают, было ли старое состояние найдено в
            ;; новой версии (п. 6.5 ТЗ).
            ((= r t)
             (if phit (setq restored (1+ restored)) (setq missing (1+ missing))))
            ((KG-StrEq r "НЕ НАЙДЕН") (setq retry (cons pv retry)))
            ((KG-StrEq r "НЕТ ПРЕДСТАВЛЕНИЯ")
             (setq noanon (1+ noanon))
             ;; Текст -- только на первые пять случаев: на чертеже со 100
             ;; экземплярами и 45 вложенными это 4500 одинаковых
             ;; предупреждений, командная строка их не вмещает. Сколько
             ;; всего -- отдельной строкой отчёта.
             (if (< noanon 6)
               (setq warns
                 (cons (strcat "Блок: " (KG-CdrCI "eff" inst)
                               "\nВложенный блок: " pn
                               "\nУ экземпляра нет анонимного "
                               "представления, состояние вложенного блока \""
                               (KG-AsString pstate)
                               "\" установить только для него нельзя.")
                       warns))))
            (r
             ;; состояние установлено; счётчики различают, было ли старое
             ;; состояние найдено в новой версии (п. 6.5 ТЗ)
             (if phit
               (setq restored (1+ restored))
               (setq missing (1+ missing))))
            (t
             (princ (strcat "\nОШИБКА: состояние видимости \""
                            (KG-AsString pstate)
                            "\" не установлено во вложенном блоке \"" pn
                            "\" экземпляра \"" (KG-CdrCI "eff" inst)
                            "\" (handle " (KG-AsString nh) ")."))))
          (if pwarn
            (setq warns
              (cons (strcat "Блок: " (KG-CdrCI "eff" inst)
                            "\nВложенный блок: " pn
                            "\n" pwarn)
                    warns))
          )
        )
        (foreach pv retry
          (setq pn (car pv))
          (setq pstate (nth 0 (cdr pv)))
          (setq phit (nth 1 (cdr pv)))
          (setq r (KG_EXSetNestedVisibility nh pn pstate))
          (cond
            ((= r t)
             (if phit (setq restored (1+ restored)) (setq missing (1+ missing))))
            ((KG-StrEq r "НЕТ ПРЕДСТАВЛЕНИЯ") (setq noanon (1+ noanon)))
            (t
             ;; второй проход тоже не нашёл вложенную вставку: такого блока
             ;; в новом определении нет, состояние перенести некуда
             (setq notfound (1+ notfound))
             (setq warns
               (cons (strcat "Блок: " (KG-CdrCI "eff" inst)
                             "\nВложенный блок: " pn
                             "\nВ новой версии такого вложенного блока нет, "
                             "состояние \"" (KG-AsString pstate)
                             "\" не перенесено.")
                     warns))))
        )
        (KG-SubT1 "замена: вложенная видимость" kg-t0)
        (setq kg-t0 (KG-SubT0))
        (KG_EXDeleteInstance old)
        (KG-SubT1 "замена: удаление старого" kg-t0)
        (setq cnt (1+ cnt))
        (setq out (cons nh out))
      )
      (if doone
        (princ (strcat "\nОШИБКА: не удалось создать экземпляр \"" tgt
                       "\" вместо handle " (if old old "?")
                       " -- старый экземпляр оставлен без изменений."))
      )
    )
    ;; 72.3: каждые 25 экземпляров списка -- уборка мусора: запись
    ;; динамических свойств создаёт много отработанных COM-объектов.
    (setq gcnt (1+ gcnt))
    (if (zerop (rem gcnt 25)) (gc))
  )
  (list
    (cons "replaced" cnt)
    (cons "space-unknown" nospace)
    (cons "vis-restored" restored)
    (cons "vis-missing" missing)
    (cons "vis-notfound" notfound)
    (cons "vis-noanon" noanon)
    (cons "nested-vis-n" nvread)
    (cons "nested-from-u" nfromu)
    (cons "nested-from-def" nfromdef)
    (cons "dyn-read" dynread)
    (cons "dyn-restored" dynrestored)
    (cons "warnings" (reverse warns))
    (cons "newhandles" (reverse out))
  )
)

;; Шаг 4. Перепривязать оставшиеся вложенные вхождения (те, что живут
;; внутри сторонних определений) и отдельно стоящие экземпляры на новые определения.
(defun KG-Step_RewireNested (model renames / tgt n eff h dyn nv att sp e newh)
  (setq n 0)
  (foreach r renames
    (setq tgt (nth 0 r))
    (foreach ins (KG-ModelInsts model)
      (setq eff (KG-CdrCI "eff" ins))
      (if (KG-StrEq eff (nth 1 r))
        (progn
          (setq h (KG-CdrCI "handle" ins))
          (setq sp (KG-CdrCI "space" ins))
          (if (and sp (/= (KG-AsString sp) "") (not (KG-StrEq (KG-AsString sp) "nil"))
                   (not KG-TESTING) (handent (KG-AsString h)))
            ;; Это экземпляр на чертеже (в модели или на листе) -- пересоздаём его на месте
            ;; с новым определением и полным переносом динамических свойств и видимости!
            (progn
              (setq e (handent (KG-AsString h)))
              (setq newh (KG-RecreateInstanceSamePlace e tgt))
              (if newh (setq n (1+ n)))
            )
            ;; Это вложенное вхождение внутри определения блока (или режим тестирования)
            (if (KG_EXSetEffectiveName h tgt)
              (progn
                ;; Снимок содержимого этой правки не видел: запись
                ;; определения в KG-RAW-NESTED больше не верна.
                (KG-RawNestedDrop (KG-DefOwnerName h))
                ;; Восстанавливаем динамические свойства, вложенную видимость и атрибуты
                (setq dyn (KG-CdrCI "dyn-props" ins))
                (if dyn (KG_EXRestoreDynProps h dyn))
                (setq nv (KG-CdrCI "nested-vis" ins))
                (if nv
                  (foreach pair nv
                    (KG_EXSetNestedVisibility h (car pair) (cdr pair))
                  )
                )
                (setq att (KG-CdrCI "attrs" ins))
                (if (and att (not KG-TESTING) (handent (KG-AsString h)))
                  (KG-Safe '(lambda () (KG-SetAttributeValues (vlax-ename->vla-object (handent (KG-AsString h))) att)) nil)
                )
                (setq n (1+ n))
              )
            )
          )
        )
      )
    )
  )
  n
)

;; Шаг 8г (сборка 71.3). Снять определения семьи, заменённые актуальной
;; версией: если под новым именем определение есть, старое больше не нужно --
;; именно это и означает «обновить определение» при нуле вставок. Снимается
;; только имя без ссылок: занятое определение AutoCAD удалить не даст, и оно
;; остаётся (п. 8.4 ТЗ -- занятое не трогаем), а в отчёте видно, что осталось.
(defun KG-Step_RetireOldDefs (model base newiter mastername arrived
                              / retired left nm var tgt)
  (setq retired nil left nil)
  (if (KG-FlexFamilyP base newiter)
    (foreach dp (KG-FindOldFamilyDefs model base newiter)
      (setq nm (car dp))
      (setq var (nth 2 (cdr dp)))
      (setq tgt (KG-MakeName base newiter var))
      (if (and (not (KG-StrEq nm tgt))                     ; не новое имя
               (not (KG-StrEq nm (KG-AsString mastername))) ; и не мастер
               (not (KG-StrInterCI (list nm) arrived))      ; новый под этим
               (KG_EXDefExists tgt))                        ; замена есть
        (if (KG-Safe '(lambda () (KG_EXDeleteDef nm)) nil)
          (setq retired (cons nm retired))
          (setq left (cons nm left))
        )
      )
    )
  )
  (cons (reverse retired) (reverse left))
)

;; Шаг 5. Убрать технический экземпляр и решить судьбу старых определений.
;; По п. 8.4 и 14.4 ТЗ неиспользуемые определения автоматически НЕ удаляются,
;; поэтому по умолчанию они остаются под именем "имя~~<итерация-источника>".
(defun KG-Step_Cleanup (renames techhandle / out kept nm)
  (setq out nil kept nil)
  (if techhandle (KG_EXDeleteInstance techhandle))
  (foreach r renames
    (setq nm (nth 1 r))
    (if (and KG-DELETE-OLD-DEFS (KG_EXDeleteDef nm))
      (setq out (cons nm out))
      (setq kept (cons (strcat (nth 0 r) " -> " nm) kept))
    )
  )
  (if kept
    (if (<= (length kept) 3)
      (princ (strcat "\nСтарых определений в резерве (удаляются через PURGE): " (KG-JoinNames kept)))
      (princ (strcat "\nСтарых определений переведено в резерв (удаляются через PURGE): " (itoa (length kept))))
    )
  )
  (reverse out)
)

;;;; Запасной путь режима A: из буфера не пришло ни одного определения, но
;;; пользователь мог вставить мастер-блок руками ДО запуска команды.
;;;
;;; Это важный случай: при ручной вставке AutoCAD отбрасывает вложенные
;;; определения с уже занятыми именами и подставляет существующие, поэтому
;;; мастер-версия оказывается собранной из СТАРОГО содержимого. Интегрировать
;;; по ней нельзя -- нужно отменить вставку и дать команде вставить самой.
;;;
;;; snap0      -- снимок экземпляров до запроса «Мастер-блок:»
;;; beforedefs -- снимок таблицы блоков до любых изменений
;;; model      -- текущая модель чертежа
;;;
;;; Возврат:
;;;   (T mastername handle base iter) -- мастер-версия найдена и пригодна;
;;;   (nil текст-сообщения)           -- продолжать нельзя.
(defun KG-FallbackMasterFromDrawing (snap0 beforedefs model
                                     / newinst cand m nm p names nested stale)
  (setq newinst (KG_EXNewInstancesSince snap0))
  (setq names nil)
  (foreach h newinst
    (setq m (KG_EXInstanceHandle h))
    (if m (setq names (cons (KG-CdrCI "eff" m) names)))
  )
  (setq names (reverse names))
  (setq cand (KG-PickMasterHandle newinst))
  (setq nm (if cand (KG-CdrCI "eff" (KG_EXInstanceHandle cand)) nil))
  (setq p (if nm (KG-ParseBlockName nm) nil))
  (cond
    ;; мастер-версия не найдена вовсе
    ((not (and p (= (nth 2 p) "")))
     (list nil
       (strcat
         "\nОШИБКА: не удалось определить мастер-версию."
         ;; Факты, а не догадка: сколько определений было и стало.
         ;; Если числа равны -- вставка не принесла ничего, и причину
         ;; надо искать в буфере обмена, а не в именах.
         (strcat "\nОпределений в таблице блоков было: "
                 (itoa (length beforedefs)) ", стало: "
                 (itoa (length (KG-Safe '(lambda () (KG_EXAllDefNames))
                                        nil))))
         "\nИз буфера не пришло ни одного нового определения. Обычно это"
         "\nзначит, что AutoCAD отбросил их как дубликаты (\"Повторное"
         "\nопределение блока ... пропущено\") -- такие имена в файле"
         "\nуже есть."
         (if names
           (strcat "\nНовые экземпляры в чертеже: " (KG-JoinNames names) ".")
           "\nНовых экземпляров в чертеже нет -- вставка не выполнена.")
         "\nЧто делать:"
         "\n  1. имя мастер-версии должно содержать номер итерации,"
         "\n     вида \"Комплект КП50 v1.5\" или \"КП50(16)\", без суффикса"
         "\n     варианта;"
         "\n  2. если блок с таким именем в файле уже есть, удалите или"
         "\n     переименуйте его ДО вставки из буфера;"
         "\n  3. после этого скопируйте мастер-блок заново и повторите"
         "\n     INTEGRATE.")))
    ;; определение мастер-версии было в файле ещё до команды
    ((member nm beforedefs)
     (list nil
       (strcat
         "\nОШИБКА: определение \"" nm "\" уже было в файле до запуска"
         "\nкоманды, из буфера не пришло ничего нового."
         "\nAutoCAD отбросил пришедшее определение как дубликат."
         "\nУдалите или переименуйте \"" nm "\" и повторите вставку.")))
    ;; определение пришло, но вложенные -- нет: содержимое старое
    ((progn
       (setq nested (KG-GetNestedBlocks model nm))
       (setq stale (KG-StrInterCI nested beforedefs))
       stale)
     (list nil
       (strcat
         "\nОШИБКА: определение \"" nm "\" пришло, но вложенные"
         "\nопределения " (KG-JoinNames stale) " остались СТАРЫМИ:"
         "\nAutoCAD отбросил их как дубликаты и подставил существующие."
         "\nИнтегрировать по такому мастеру нельзя -- получится старое"
         "\nсодержимое под новым именем."
         "\nЧто делать:"
         "\n  1. отмените свою вставку: UNDO (или Ctrl+Z) до её отмены;"
         "\n  2. запустите INTEGRATE заново и на запросе \"Мастер-блок:\""
         "\n     нажмите ENTER, ничего не выбирая;"
         "\n  3. команда сама освободит конфликтующие имена и сама вставит"
         "\n     блок из буфера -- тогда содержимое придёт новое.")))
    ;; всё в порядке: мастер пришёл, вложенные тоже новые
    (t
     (KG-Say "")
     (KG-Say "Из буфера не пришло новых определений, но в чертеже есть")
     (KG-Say "новый экземпляр мастер-версии с новым содержимым.")
     (KG-Say "Продолжаем по нему.")
     (list t nm cand (nth 0 p) (nth 1 p)))
  )
)


;; Печать длинного списка имён: первые несколько и счётчик.
;;
;; На реципиенте со 100 блоками списки «пришло из буфера» (111 имён),
;; «освобождено» (105) и «кандидаты на очистку» (43) занимали больше места,
;; чем весь остальной отчёт, и лог не помещался в сообщение. Полностью
;; прятать их нельзя: по именам видно, не тронуто ли чужое семейство.
;; Поэтому печатается начало списка и остаток числом.
(defun KG-PrincList (lst limit / i)
  (setq i 0)
  (foreach nm lst
    (if (< i limit)
      (progn
        (princ (strcat "\n  " (KG-AsString nm)))
        (setq i (1+ i)))
    )
  )
  (if (> (length lst) limit)
    (princ (strcat "\n  ... и ещё " (KG-NumStr (- (length lst) limit))))
  )
  (length lst)
)

(defun KG-SayList (lst limit / i)
  (setq i 0)
  (if (null lst)
    (KG-Say "  (ни одного)")
    (foreach nm lst
      (if (< i limit)
        (progn
          (KG-Say (strcat "  " (KG-AsString nm)))
          (setq i (1+ i)))
      )
    )
  )
  (if (> (length lst) limit)
    (KG-Say (strcat "  ... и ещё " (KG-NumStr (- (length lst) limit)))))
  (length lst)
)

(defun KG-ReportArrived (beforedefs afterdefs / newdefs gone nm)
  (setq newdefs (KG-Step_DetectArrived beforedefs afterdefs))
  (setq gone (KG-StrDiffCI beforedefs afterdefs))
  (KG-Say (strcat "Из буфера получено новых определений: "
                  (KG-NumStr (length newdefs))))
  (if (and (null newdefs) (not (KG-IsAnonymousName (car afterdefs))))
    (progn
      (KG-Say "  ВНИМАНИЕ: скорее всего сработало \"Duplicate definition of")
      (KG-Say "  block ... ignored\" — AutoCAD оставил СТАРЫЕ определения.")
      (KG-Say "  Переименуйте конфликтующие определения и повторите вставку.")
    )
  )
  (if (and gone KG-TRACE)
    (progn
      (KG-Say (strcat "Освобождённые имена: " (KG-NumStr (length gone))))
      (KG-SayList gone 5)
    )
  )
)


;;;--- ОРКЕСТРАЦИЯ -----------------------------------------------------------
;;; Полный цикл интеграции. Работает только через адаптер KG_DB*/KG_EX*,
;;; поэтому одинаково исполняется и в AutoCAD, и на тестовом стенде.
;;;
;;; base       -- семейство, например "ABC1.01"
;;; newiter    -- новая итерация, например 15
;;; techhandle -- handle технического экземпляра мастер-версии (или nil)
;;; do-paste   -- T, если нужна техническая вставка из буфера (режим A)
;;;
;;; Порядок операций принципиален:
;;;   1. снимается снимок таблицы блоков ДО изменений -- по нему потом
;;;      различаются «обновить существующее вложенное» и «добавить новое»;
;;;      второй снимок делается после освобождения имён и до вставки --
;;;      только по нему видно, что пришло именно из буфера;
;;;   2. освобождаются имена, которые должно занять содержимое буфера --
;;;      иначе PASTECLIP отбросит новые определения;
;;;   3. проверяется, что мастер-версия ДЕЙСТВИТЕЛЬНО пришла из буфера;
;;;      если нет -- переименования откатываются и операция не начинается;
;;;   4. только теперь читается модель и строится план: на этом шаге
;;;      мастер-версия уже ссылается на новые вложенные определения;
;;;   5. создаются варианты, заменяются экземпляры, перепривязываются
;;;      вложенные вхождения внутри сторонних определений.
;; 72.7: чтение модели без дорогих свойств. Нужно там, где используются
;; только определения, имена, handle, пространство и геометрия.
(defun KG-ReadModelNoProps ( / res)
  (setq KG-MODEL-FAMILY nil KG-MODEL-SKIP-PROPS t)
  (setq res (KG-Safe '(lambda () (KG_DBGetModel)) nil))
  (setq KG-MODEL-SKIP-PROPS nil)
  res
)

;; 72.7: чтение модели, в котором дорогие свойства читаются только у
;; вставок семьи BASE. Чужие вставки остаются в модели без свойств.
(defun KG-ReadModelFamily (base / res)
  (setq KG-MODEL-FAMILY base KG-MODEL-SKIP-PROPS nil)
  (setq res (KG-Safe '(lambda () (KG_DBGetModel)) nil))
  (setq KG-MODEL-FAMILY nil)
  res
)

;; 72.7: снимок только вхождений, без дорогих свойств. Он нужен шагу
;; перепривязки: топ-level вставка пересоздаётся и читает себя заново,
;; а вложенные вхождения в него всё равно не попадают.
(defun KG-ReadInstancesNoProps ( / res)
  (setq KG-MODEL-FAMILY nil KG-MODEL-SKIP-PROPS t)
  (setq res (KG-Safe '(lambda () (KG-DBGetInstancesOnly)) nil))
  (setq KG-MODEL-SKIP-PROPS nil)
  res
)

(defun KG-Integrate_Model (base newiter techhandle do-paste / model mastername
                                                pre renames plan created rep
                                                deleted val warns errs arrived
                                                missing v snap beforedefs
                                                pastesnap arriveddefs stale
                                                masterfreed handlesnap
                                                eff a rewired visrest
                                                retired keepn grp kg-t0 mdl2)
  (setq errs nil)
  (setq warns nil)
  (setq KG-MODEL-FAMILY nil KG-MODEL-SKIP-PROPS nil)
  (setq mastername (KG-MakeName base newiter ""))

  ;; 1. снимок таблицы блоков ДО любых изменений. Именно по нему потом
  ;;    различаются «вложенное определение уже было в файле» (обновляем)
  ;;    и «его в файле не было» (добавляем). Снимок, сделанный после
  ;;    переименования, этого различия не даёт.
  (KG-MarkT "снимок чертежа до изменений")
  ;; 72.6: перед первым чтением модели освобождаем VLA-обёртки прошлой
  ;; семьи. Падение 72.5 на семье 2 случилось на 101-й вставке, хотя то же
  ;; состояние читалось контролем за несколько секунд до этого: причина --
  ;; накопленные COM-объекты, а не данные чертежа.
  (gc)
  ;; 72.7: в обычном прогоне C:RDB этот снимок не используется. Вставку
  ;; и освобождение имён уже сделала C:RDB, KG-PRERENAMES задан, а ветка
  ;; do-paste сюда не заходит. Полное чтение 1233 вставок здесь стоило
  ;; десятки секунд, и именно на нём падала семья 3 (handle 93173 --
  ;; *U-представление ригеля семьи 2). Читаем только там, где снимок
  ;; действительно нужен ветке do-paste.
  (if (and do-paste (null KG-PRERENAMES))
    (setq model (KG-ReadModelNoProps))
    (setq model (list (cons "defs" nil) (cons "insts" nil)
                      (cons "layouts" nil)))
  )
  (if (null model)
    (progn
      (princ (strcat "\nВНИМАНИЕ: снимок чертежа не прочитан ("
                     (KG-FailText)
                     "). Отчёт будет неполным, интеграция продолжена."))
      (setq model (list (cons "defs" nil) (cons "insts" nil)
                        (cons "layouts" nil)))
    )
  )
  ;; В режиме вставки из буфера снимок обязан быть сделан ДО того, как
  ;; C:INTEGRATE освободил имена: по нему «вложенное определение уже
  ;; было в файле» (обновляем) отличается от «его не было» (добавляем).
  ;; Снимок, снятый после переименования, путает их местами.
  (setq beforedefs (if KG-PREDEFS KG-PREDEFS (KG_EXAllDefNames)))

  ;; 2. освобождаем имена до вставки.
  ;;    В режиме вставки из буфера (do-paste) вставку выполняет команда
  ;;    C:INTEGRATE ещё до вызова этой функции, и имена освобождает тоже
  ;;    она -- она передаёт их списком prerenames. Освобождать имена здесь
  ;;    уже поздно, а переименовывать пришедшие определения нельзя:
  ;;    содержимое снова стало бы старым.
  ;; Имена уже освобождены ДО вставки (это делает C:INTEGRATE). Если
  ;; переименовать их здесь ещё раз, освобождённое имя мастер-версии
  ;; снова уйдёт в "~имя" и определение окажется пустым -- именно так
  ;; появлялся мусорный вариант "v1.5 до1.5".
  (if KG-PRERENAMES
    (setq renames KG-PRERENAMES)
    (if do-paste
      (progn
        (KG-MarkT "освобождение имён до вставки")
        (setq pre (KG-ConflictCandidates model base))
        (setq renames (KG-Step_PreRename pre newiter base model))
      )
      ;; Режим B: мастер-блок вставлен руками ДО запуска команды.
      ;; Переименовывать определения здесь поздно и опасно: вставка уже
      ;; выполнена, пришедшего из буфера ждать нечего, а переименование
      ;; оторвало бы мастер-версию от её собственных вложенных
      ;; определений -- в чертеже остался бы блок со ссылками на
      ;; «~Стойка» вместо «Стойка».
      (progn
        (setq renames nil)
        (princ (strcat "\nВНИМАНИЕ: мастер-блок вставлен вручную, вставка из "
                       "буфера внутри команды не выполнялась."
                       "\nВложенные определения в этом режиме обновить нельзя:"
                       " при ручной вставке AutoCAD подставляет уже "
                       "существующие определения с теми же именами"
                       " (\"Duplicate definition of block ... ignored\")."
                       "\nЧтобы вложенные обновились, запустите INTEGRATE и на "
                       "запросе «Мастер-блок:» нажмите Enter -- команда сама "
                       "освободит имена и вставит содержимое буфера."))
      )
    )
  )

  ;; 3. техническая вставка из буфера
  (if do-paste
    (progn
      (setq snap (KG-SnapshotDrawing))
      ;; второй снимок -- ПОСЛЕ переименования и ДО вставки: только по нему
      ;; видно, что пришло именно из буфера (иначе «пришедшими» окажутся
      ;; наши же переименованные имена)
      (setq pastesnap (KG_EXAllDefNames))
      (setq handlesnap
        (KG-Safe '(lambda () (KG_EXDefHandleSnapshot)) nil))
      ;; Имя самой мастер-версии тоже обязано быть свободным ДО вставки,
      ;; иначе AutoCAD отбрасывает пришедшее определение
      ;; ("Duplicate definition of block ... ignored") -- именно так
      ;; команда получила «НЕ получена из буфера» на реальном чертеже.
      (setq masterfreed
        (KG-Safe '(lambda () (KG-FreeMasterName mastername newiter)) nil))
      (setq KG-MASTER-FREED masterfreed)
      ;; 71.9: переименование мастер-версии -- тоже часть состояния,
      ;; которое обязано пережить жёсткое падение. Под стендом журнала нет:
      ;; KG-JournalWrite определён только в разделе 8.
      (if (not KG-TESTING) (KG-JournalWrite))
      (if (not (KG_EXPasteAtOrigin))
        (setq errs (cons "Не удалось вставить содержимое буфера обмена." errs))
      )
      (setq arriveddefs (KG-Step_DetectArrived pastesnap (KG_EXAllDefNames)))
      ;; Сравнение имён ненадёжно: на реальном чертеже оно сказало, что
      ;; мастер-версия не пришла, хотя определение в файле было. Handle
      ;; определения меняется, когда AutoCAD заменяет его пришедшим,
      ;; поэтому список дополняется по снимку handle.
      (if handlesnap
        (foreach nm (KG-Safe '(lambda () (KG-ArrivedByHandle handlesnap)) nil)
          (if (not (member nm arriveddefs))
            (setq arriveddefs (cons nm arriveddefs))
          )
        )
      )
      ;; Имена, которых буфер не принёс, возвращаются на место --
      ;; иначе сторонние семейства и старые вложенные определения
      ;; остались бы под служебными именами «~имя».
      (setq renames (KG-Step_RollbackNotArrived renames arriveddefs))
      ;; карта handle -> пространство построена до вставки и не знает о
      ;; техническом экземпляре; без перестроения он не читается
      (KG-MarkT "перестроение карты пространств после вставки")
      (KG-RefreshSpaceMap)
      ;; поиск технического экземпляра не должен ронять команду:
      ;; без него INTEGRATE просто не найдёт вставку и скажет об этом
      (KG-MarkT "поиск технического экземпляра среди новых вхождений")
      (setq techhandle
        (KG-Safe '(lambda () (KG-PickMasterHandle (KG_EXNewInstancesSince snap))) nil))
      (if (null techhandle)
        (KG-MarkT "технический экземпляр не найден")
        (KG-MarkT (strcat "технический экземпляр: " (KG-AsString techhandle)))
      )
      ;; Мастер-версия пришла из буфера тогда и только тогда, когда её имя
      ;; было освобождено нами и после вставки определение снова существует.
      ;; Сверять это по снимку таблицы блоков нельзя: снимок делается до
      ;; освобождения имени и в реальном AutoCAD на таком сравнении
      ;; команда уже получала ложное «НЕ получена из буфера».
      (setq arrived
        (if masterfreed
          (KG_EXDefExists mastername)
          (and (member mastername arriveddefs) t)))
      (if (and (null arrived) masterfreed)
        (progn
          ;; вставка не дала мастер-версию -- возвращаем имя на место,
          ;; иначе определение осталось бы переименованным
          (KG-Safe '(lambda () (KG-RestoreMasterName masterfreed)) nil)
          (setq KG-MASTER-FREED nil)
          (princ (strcat "\nВНИМАНИЕ: мастер-версия из буфера не пришла, "
                         "определение \"" mastername "\" возвращено как было."))
        )
      )
    )
    (progn
      ;; режим B: мастер уже в чертеже. Список пришедших определений
      ;; берётся у вызывающей стороны -- без него проверка «осталось
      ;; старым» сочла бы старым вообще всё.
      (if KG-ARRIVED (setq arriveddefs KG-ARRIVED))
      (setq arrived t)
    )
  )

  ;; 4. модель ПОСЛЕ вставки
  (KG-MarkT "чтение модели после вставки")
  (setq kg-t0 (KG-SubT0))
  ;; 72.7: полное чтение модели нужно только для плана и замены. Дорогие
  ;; свойства читаем только у вставок своей семьи: чужие в план не входят.
  (setq model (KG-ReadModelFamily base))
  (if (null model)
    (progn
      (princ (strcat "\nВНИМАНИЕ: снимок чертежа не прочитан ("
                     (KG-FailText)
                     "). Отчёт будет неполным, интеграция продолжена."))
      (setq model (list (cons "defs" nil) (cons "insts" nil)
                        (cons "layouts" nil)))
    )
  )
  (KG-SubT1 "семья: чтение модели после вставки (работа)" kg-t0)

  ;; Сколько экземпляров каждого варианта уже стоит на новой итерации.
  ;; Считается ДО замены и без технического экземпляра: иначе отчёт
  ;; сравнит «стало» со счётчиком только старых экземпляров и покажет
  ;; ложное расхождение и ложную потерю.
  ;; Для блоков без версии (newiter = "") все существующие экземпляры -- старые и заменяются,
  ;; поэтому KG-ALREADYNEW = nil.
  (setq KG-ALREADYNEW nil)
  (if (/= (KG-IterToStr newiter) "")
    (foreach ins (KG-ModelInsts model)
      (setq eff (KG-CdrCI "eff" ins))
      (if (and (KG-IsIntegrationName eff base newiter)
               (not (KG-StrEq (KG-CdrCI "handle" ins) techhandle)))
        (progn
          (setq p (KG-ParseBlockName eff))
          (setq v (if p (nth 2 p) ""))
          (setq a (KG-AssocCI v KG-ALREADYNEW))
          (if a
            (setq KG-ALREADYNEW (KG-SetAssoc v (1+ (cdr a)) KG-ALREADYNEW))
            (setq KG-ALREADYNEW (cons (cons v 1) KG-ALREADYNEW))
          )
        )
      )
    )
  )

  (if (not (and arrived (KG-FindDef model mastername)))
    (progn
      ;; имя мастер-версии возвращается ПЕРЕД откатом вложенных имён:
      ;; иначе откат мог бы переименовать определение обратно в имя,
      ;; которое всё ещё занято нашей временной копией мастера
      (if masterfreed
        (KG-Safe '(lambda () (KG-RestoreMasterName masterfreed)) nil))
      (KG-Step_RollbackRename renames)
      (list
        (cons "errors"
          (cons (if arrived
                  (strcat "Определение мастер-версии \"" mastername
                          "\" не найдено в чертеже.")
                  (strcat "Мастер-версия \"" mastername "\" НЕ получена из "
                          "буфера: AutoCAD отбросил пришедшее определение, "
                          "потому что такое имя уже занято в текущем файле "
                          "(\"Duplicate definition of block ... ignored\"). "
                          "Переименуйте или удалите конфликтующее определение, "
                          "скопируйте мастер-блок заново и повторите команду."))
                errs))
        (cons "renames" nil)
        (cons "rolled-back" renames)
      )
    )
    (progn
      ;; 5. план
      (KG-MarkT "построение плана интеграции")
      (setq kg-t0 (KG-SubT0))
      ;; Снимок таблицы блоков ДО вставки передаётся ВСЕГДА, когда он есть,
      ;; а не только когда вставку делает сама эта функция. Иначе
      ;; классификация «обновить / добавить» считается по таблице ПОСЛЕ
      ;; вставки: все вложенные определения к тому моменту уже в файле,
      ;; и план решает, что обновлять нечего. Именно так на реальном
      ;; чертеже получилось «Обновлено вложенных: 0» при 42 «новых».
      (setq plan (KG-BuildIntegrationMap model mastername beforedefs))
      ;; Если есть технический экземпляр (вставка из буфера), исключаем его из списка заменяемых
      (if techhandle
        (progn
          (setq plan
            (KG-SetAssoc "instances"
              (vl-remove-if
                '(lambda (pr) (KG-StrEq (KG-CdrCI "handle" (car pr)) techhandle))
                (cdr (assoc "instances" plan)))
              plan))
          (setq plan
            (KG-SetAssoc "scan"
              (KG-SetAssoc "groups"
                (mapcar
                  '(lambda (g)
                     (cons (car g)
                           (vl-remove-if
                             '(lambda (pr) (KG-StrEq (KG-CdrCI "handle" (car pr)) techhandle))
                             (cdr g))))
                  (cdr (assoc "groups" (cdr (assoc "scan" plan)))))
                (cdr (assoc "scan" plan)))
              plan))
        )
      )
      (setq KG-PLAN plan)
      (KG-SubT1 "семья: план (работа)" kg-t0)
      ;; 6. что из вложенных определений реально пришло
      (setq missing nil)
      (foreach v (cdr (assoc "nested-all" plan))
        (if (not (KG-FindDef model v)) (setq missing (cons v missing)))
      )
      (if missing
        (setq warns
          (cons (strcat "Не получены из буфера вложенные определения: "
                        (KG-JoinNames missing)
                        ". Их содержимое осталось прежним.")
                warns))
      )
      ;; вложенные, которые AutoCAD подставил старыми (имя было занято
      ;; и определение не освободилось) -- содержимое НЕ обновилось
      (if beforedefs
        (progn
          (setq stale nil)
          (foreach v (cdr (assoc "nested-to-update" plan))
            (if (not (member v arriveddefs)) (setq stale (cons v stale)))
          )
          (if stale
            (setq warns
              (cons (strcat "ВНИМАНИЕ: вложенные определения "
                            (KG-JoinNames (reverse stale))
                            " вставлены СТАРЫМИ (AutoCAD подставил "
                            "существующие вместо пришедших). Обновите их "
                            "вручную или освободите имена и повторите.")
                    warns))
          )
        )
      )
      ;; 6. варианты
      (KG-MarkT "создание определений вариантов")
      (setq kg-t0 (KG-SubT0))
      (setq created (KG-Step_CreateVariants plan))
      (KG-SubT1 "семья: варианты (работа)" kg-t0)
      ;; 7. экземпляры
      (KG-MarkT "замена экземпляров и перенос состояний видимости")
      (setq kg-t0 (KG-SubT0))
      (setq rep (KG-Step_ReplaceInstances model plan
                     (cdr (assoc "instances" plan))))
      (KG-SubT1 "семья: замена экземпляров (работа)" kg-t0)
      ;; 8. перепривязка вложенных вхождений внутри сторонних определений
      (KG-MarkT "перепривязка вложенных вхождений")
      ;; 72.3: уборка мусора после замены экземпляров -- перед тяжёлым
      ;; чтением модели. Именно здесь на крупном чертеже падало 0xC0000005.
      (gc)
      (setq kg-t0 (KG-SubT0))
      (setq mdl2 (KG-ReadInstancesNoProps))
      (KG-SubT1 "семья: чтение модели (вложенные)" kg-t0)
      ;; 72.5: снимок содержимого определений -- только DXF. По нему карта
      ;; ссылок строится без повторного обхода (см. KG-RefMapBuild).
      (setq kg-t0 (KG-SubT0))
      (setq KG-RAW-NESTED (KG-Safe '(lambda () (KG-RawNestedBuild)) nil))
      (KG-SubT1 "семья: снимок содержимого определений" kg-t0)
      (setq kg-t0 (KG-SubT0))
      (KG-Step_RewireNested mdl2 renames)
      (KG-SubT1 "семья: перепривязка вложенных (работа)" kg-t0)
      ;; 8б. перепривязка ссылок внутри определений на прежние имена.
      ;; Идёт ДО очистки: освобождённые здесь служебные определения «~ИМЯ»
      ;; очистка снимет тем же прогоном.
      (KG-MarkT "перепривязка ссылок на прежние имена")
      (setq kg-t0 (KG-SubT0))
      (setq rewired (KG-Safe '(lambda () (KG-Step_RewireDefs renames)) 0))
      (KG-SubT1 "семья: перепривязка ссылок (работа)" kg-t0)
      ;; 8в. возврат состояний видимости вложенных блоков подменённым
      ;; определениям. Идёт после перепривязки: к этому моменту вложенные
      ;; вставки уже указывают на прежние имена.
      (KG-MarkT "возврат состояний вложенных блоков")
      (setq kg-t0 (KG-SubT0))
      (setq visrest (KG-Safe '(lambda () (KG-Step_RestoreNestedVis renames))
                             (list 0 0 0)))
      (KG-SubT1 "семья: возврат состояний (работа)" kg-t0)
      ;; 8г. старые определения семьи, заменённые актуальной версией,
      ;; снимаются: иначе рядом с новой версией остаётся прежняя и
      ;; «обновление» определения при нуле вставок не видно.
      (KG-MarkT "снятие старых определений семейства")
      (gc)
      (setq kg-t0 (KG-SubT0))
      (setq mdl2 (KG-ReadModelNoProps))
      (KG-SubT1 "семья: чтение модели (старые)" kg-t0)
      (setq kg-t0 (KG-SubT0))
      (setq retired
        (KG-Safe '(lambda ()
                    (KG-Step_RetireOldDefs
                      mdl2 base newiter mastername arriveddefs))
                 (cons nil nil)))
      (KG-SubT1 "семья: снятие старых (работа)" kg-t0)
      ;; 9. технический экземпляр и старые определения
      (KG-MarkT "удаление технического экземпляра")
      (setq kg-t0 (KG-SubT0))
      (setq deleted (KG-Step_Cleanup renames techhandle))
      (KG-SubT1 "семья: удаление тех.экземпляра (работа)" kg-t0)
      ;; 10. контроль
      (KG-MarkT "контроль результата")
      (gc)
      (setq kg-t0 (KG-SubT0))
      (setq mdl2 (KG-ReadModelNoProps))
      (KG-SubT1 "семья: чтение модели (контроль)" kg-t0)
      (setq val (KG-ValidateIntegration mdl2 base newiter
                   (cdr (assoc "groups" (cdr (assoc "scan" plan))))))
      ;; 71.3: что очистка обязана сохранить -- мастер-версию и определения
      ;; всех вариантов этой семьи (в том числе созданные без вставок).
      (setq keepn nil)
      (foreach grp (cdr (assoc "groups" (cdr (assoc "scan" plan))))
        (setq keepn (cons (KG-MakeName base newiter (car grp)) keepn))
      )
      (if (and mastername (not (KG-StrInterCI (list mastername) keepn)))
        (setq keepn (cons mastername keepn))
      )
      (setq keepn (reverse keepn))
      (setq KG-KEEPNAMES
        (append keepn
                (vl-remove-if '(lambda (x) (KG-StrInterCI (list x) keepn))
                              KG-KEEPNAMES)))
      (list
         (cons "plan" plan)
         (cons "renames" renames)
         (cons "created" created)
         (cons "replaced" rep)
         ;; 71.3: судьба старых определений семьи
         (cons "retired" (car retired))
         (cons "retire-left" (cdr retired))
         ;; 71.3: имена, которые обязана сохранить очистка
         (cons "keep-names" keepn)
         (cons "deleted-defs" deleted)
         (cons "rewired" (KG-AsNum rewired 0))
         (cons "vis-nested-restored" visrest)
         (cons "rewired-skip" (reverse KG-REWSKIP))
        ;; что из запланированного обновления вложенных НЕ обновилось:
        ;; AutoCAD подставил старое определение вместо пришедшего
        (cons "nested-stale" (reverse stale))
        (cons "arrived" arriveddefs)
        (cons "freed" KG-FREED-N)
        (cons "candidates" KG-PRE-CANDIDATES)
        (cons "rename-failed" KG-PRENAME-FAILED)
        (cons "validation" val)
        (cons "warnings" (append warns (cdr (assoc "warnings" rep))))
        (cons "errors" errs)
        ;; семейство нужно отчёту: по нему считается, сколько экземпляров
        ;; реально стоит в чертеже
        (cons "base" base)
      )
    )
  )
)

;; Почему указанное вхождение не годится в мастер-версию.
;; Два принципиально разных случая, и текст должен их различать:
;;   * в имени вообще нет номера итерации -- имя не по схеме;
;;   * номер есть, но есть и суффикс варианта -- это вариант, а не мастер.
(defun KG-MasterRejectMsg (eff / p)
  (setq eff (KG-AsString eff))
  (setq p (KG-ParseBlockName eff))
  (cond
    ((null p)
     (strcat "\nВНИМАНИЕ: \"" eff "\" не подходит под схему именования."
             "\nВ имени нет номера итерации."
             "\nГодятся имена вида \"Комплект КП50 v1.5\" или \"КП50(16)\"."
             "\nНомер новой итерации берётся только из имени мастер-версии."))
    (t
     (strcat "\nВНИМАНИЕ: \"" eff "\" -- это вариант \"" (nth 2 p)
             "\" итерации " (KG-IterToStr (nth 1 p)) ", а не мастер-версия."
             "\nМастер-версия называется \""
             (KG-MakeName (nth 0 p) (nth 1 p) "") "\"."))
  )
)

;;; РАЗДЕЛ 8. ИСПОЛНЯЮЩИЙ СЛОЙ AUTOCAD
;;;
;;; Загружается только внутри AutoCAD. На тестовом стенде эти функции
;;; подставляются стендом (см. tests/run_tests.py).
;;;---------------------------------------------------------------------------

;; Вложенная вставка внутри определения по её эффективному имени.
;; Возвращает vla-объект или nil. Обход только через entget: COM-обход
;; содержимого определений на реальном чертеже дал 0xC0000005.
;; Вставки внутри определения по НЕСКОЛЬКИМ именам за ОДИН обход.
;; Возврат: alist «имя из keys -> объект вставки (vla-object)».
;;
;; Зачем пакетно. KG-DefInsertByName обходил определение заново ради
;; каждого имени-состояния, и на КАЖДУЮ вставку читалось EffectiveName
;; через COM (два COM-вызова). Живой прогон 71.4: шаг «возврат состояний
;; вложенных блоков» занял 24.9 с. Теперь обход один на определение, а
;; имя анонимного представления читается из паспорта по DXF (72.6),
;; без COM; кэш по группе 2 остаётся.
(defun KG-DefInsertsForKeys (defname keys / e ed o nm out g2 ecache k hits left)
  (setq out nil ecache nil left (length keys))
  (setq e (KG-Safe '(lambda () (KG-DefEnt defname)) nil))
  (if e
    (while (and (> left 0)
                (setq e (KG-Safe '(lambda () (entnext e)) nil))
                (setq ed (KG-Safe '(lambda () (entget e)) nil))
                (/= (KG-AsString (cdr (assoc 0 ed))) "ENDBLK"))
      (if (KG-StrEq (KG-AsString (cdr (assoc 0 ed))) "INSERT")
        (progn
          (setq g2 (KG-AsString (cdr (assoc 2 ed))))
          (setq o nil)
          (setq hits nil)
          ;; Прямое сравнение по группе 2 -- без COM. Совпадение с учётом
          ;; служебной отметки ловит и «~Стойка КП50» против «Стойка КП50».
          (foreach k keys
            (if (and (not (assoc k out)) (KG-NestedKeyMatch g2 k))
              (setq hits (cons k hits))
            )
          )
          ;; Анонимное представление: в группе 2 заводское «*U123», а
          ;; эффективное имя -- родительский блок; читается из паспорта
          ;; по DXF и кэшируется по группе 2.
          (if (and (null hits) (= (substr g2 1 1) "*"))
            (progn
              (setq nm (cdr (assoc g2 ecache)))
              (if (null nm)
                (progn
                  ;; 72.6: имя -- из паспорта по DXF; VLA-объект нужен
                  ;; только найденным вставкам (ниже).
                  (setq nm (KG-EffNameOfEd ed g2 e))
                  (setq ecache (cons (cons g2 nm) ecache))
                )
              )
              (foreach k keys
                (if (and (not (assoc k out)) (KG-NestedKeyMatch nm k))
                  (setq hits (cons k hits))
                )
              )
            )
          )
          (if hits
            (progn
              (if (null o)
                (setq o (KG-Safe '(lambda () (vlax-ename->vla-object e)) nil))
              )
              (if o
                (foreach k hits
                  (setq out (cons (cons k o) out))
                  (setq left (1- left))
                )
              )
            )
          )
        )
      )
    )
  )
  (reverse out)
)

(defun KG-DefInsertByName (defname nestedname / e ed obj nm out g2)
  (setq out nil)
  (setq e (KG-Safe '(lambda () (KG-DefEnt defname)) nil))
  (if e
    (while (and (not out)
                (setq e (KG-Safe '(lambda () (entnext e)) nil))
                (setq ed (KG-Safe '(lambda () (entget e)) nil))
                (/= (KG-AsString (cdr (assoc 0 ed))) "ENDBLK"))
      (if (KG-StrEq (KG-AsString (cdr (assoc 0 ed))) "INSERT")
        (progn
          (setq g2 (KG-AsString (cdr (assoc 2 ed))))
          ;; 71.5. Сначала прямое сравнение по группе 2: она и есть имя
          ;; вложения, а KG-NestedKeyMatch учитывает служебную отметку
          ;; «~». COM-чтение EffectiveName осталось ЗАПАСНЫМ путём и
          ;; вызывается только для анонимных представлений («*U123»): у
          ;; них в группе 2 заводское имя представления, а эффективное
          ;; имя -- родитель. Прежний код читал EffectiveName у КАЖДОЙ
          ;; вставки; на этом шаг возврата состояний и стоил 24.9 с.
          (if (KG-NestedKeyMatch g2 nestedname)
            (setq out (KG-Safe '(lambda () (vlax-ename->vla-object e)) nil))
            (if (= (substr g2 1 1) "*")
              (if (KG-NestedKeyMatch (KG-EffNameOfEd ed g2 e) nestedname)
                (setq out (KG-Safe '(lambda () (vlax-ename->vla-object e)) nil))
              )
            )
          )
        )
      )
    )
  )
  out
)

;; Эффективное имя объекта-вхождения. Всегда строка: у некоторых
;; объектов не читается ни EffectiveName, ни Name, и тогда ошибка
;; перехвата уезжала дальше в strcat как «неверный тип аргумента: stringp».
(defun KG-EffectiveNameOf (obj / n)
  (setq n (vl-catch-all-apply '(lambda () (vla-get-EffectiveName obj))))
  (if (KG-IsErr n)
    (setq n (vl-catch-all-apply '(lambda () (vla-get-Name obj)))))
  (if (KG-IsErr n)
    (KG-AsString (cdr (assoc 2 (entget (vl-catch-all-apply
                                         '(lambda () (vlax-vla-object->ename obj)))))))
    (KG-AsString n)
  )
)


;; Эффективное имя вставки по DXF. У анонимного представления (*U…)
;; настоящее имя лежит в паспорте: расширенный словарь вставки ->
;; AcDbBlockRepresentation -> AcDbRepData -> 340 на запись базового
;; определения. Тем же путём уже ходит лечение паспортов (KG-RepHealChain),
;; поэтому отдельного COM-вызова не нужно.
;;
;; Проверено на крупном файле: паспорт с именем есть у всех 691 верхней и
;; 494 вложенных *U-вставок и до замены семьи, и после неё -- COM на
;; чтении модели не вызывается. Если паспорта нет (старый или
;; повреждённый файл, стенд), остаётся прежний путь через EffectiveName.
(defun KG-EffNameOfEd (ed defnm e / d sec sub dat rec r nm o)
  (setq nm (KG-AsString defnm))
  (if (and (> (strlen nm) 0) (= (substr nm 1 1) "*"))
    (progn
      ;; 360 -- расширенный словарь вставки (первый 360 в entget).
      (setq d (cdr (assoc 360 ed)))
      (setq sec (if d
                  (KG-Safe '(lambda () (dictsearch d "AcDbBlockRepresentation")) nil)))
      (setq sub (if sec (KG-Safe '(lambda () (cdr (assoc -1 sec))) nil)))
      (setq dat (if sub
                  (KG-Safe '(lambda () (cdr (assoc -1 (dictsearch sub "AcDbRepData"))))
                           nil)))
      (setq rec (if dat (KG-Safe '(lambda () (cdr (assoc 340 (entget dat)))) nil)))
      (setq r (if rec (KG-Safe '(lambda () (cdr (assoc 2 (entget rec)))) nil)))
      (if (and r (/= (KG-AsString r) "") (/= (substr (KG-AsString r) 1 1) "*"))
        (setq nm (KG-AsString r))
        ;; Паспорта нет (старый или повреждённый файл) -- прежний путь
        ;; через COM. В крупном файле паспорт есть у всех *U, поэтому
        ;; на чтении модели этот вызов не выполняется.
        (if e
          (progn
            (setq o (KG-Safe '(lambda () (vlax-ename->vla-object e)) nil))
            (if o
              (setq nm (KG-AsString (KG-EffectiveNameOf o)))
            )
          )
        )
      )
    )
  )
  nm
)

;; То же, когда на руках только ename (одиночные вызовы RDBDIAG).
(defun KG-EffNameOfEnt (e / ed)
  (setq ed (KG-Safe '(lambda () (entget e)) nil))
  (if ed
    (KG-EffNameOfEd ed (KG-AsString (cdr (assoc 2 ed))) e)
    ""
  )
)

;;; Снять маркер успешной выборки с карты ссылок.
;;;
;;; KG-EXRefHolders возвращает ("OK" . карта), чтобы «выборка не
;;; сработала» (nil) отличалась от «вставок нет» (("OK")). Маркер живёт
;;; только в car: любой обход карты -- assoc, vl-some, foreach -- на
;;; строке "OK" спотыкается. В сборке 40 маркер снимался внутри
;;; KG-CleanupCounts и KG-CleanupOrphans, но в контроле после PURGE карта
;;; шла в KG-CdrCI напрямую -- и команда снова падала с «неверный тип
;;; аргумента: consp "OK"». Снимать надо там, где карта получена.
(defun KG-Unmark (x / )
  (if (and x (KG-StrEq (KG-AsString (car x)) "OK")) (cdr x) x)
)

;;; Текст «кто держит определение» для контроля после очистки.
;;; Отдельная функция, чтобы печатающий код не обходил карту сам:
;;; обход с маркером в car -- это и есть падение consp "OK".
(defun KG-CleanupHolderText (holders nm / hh)
  (setq hh (KG-CdrCI (KG-AsString nm) (KG-Unmark holders)))
  (if hh (KG-JoinNames hh) "(прямых вставок нет)")
)

;;; Ename записи блока (самого BLOCK-примитива определения).
;;;
;;; tblobjname на реальном чертеже ответил nil на ВСЕ 37 сиротских *U, и
;;; очистка напечатала «BLOCK не найден» 37 раз подряд: имена приходят из
;;; COM-коллекции Blocks (KG_EXAllDefNames), а ename программа брала из
;;; таблицы блоков. Запасной путь -- tblsearch: у записи таблицы группа -2
;;; и есть ename нужного примитива. В отличие от обхода tblnext + entnext
;;; по всей таблице (на нём чертёж падал с 0xC0000005) tblsearch читает
;;; одну запись и содержимое определений не обходит.
(defun KG-DefEntViaCom (defname / b e)
  ;; Третий путь к ename определения: COM-коллекция Blocks. Она же --
  ;; источник имён (KG_EXAllDefNames), поэтому имя из неё здесь
  ;; находится всегда; остаётся превратить объект в ename.
  (setq b (KG-Safe '(lambda () (KG-BlockObj (KG-AsString defname))) nil))
  (if b
    (setq e (KG-Safe '(lambda () (vlax-vla-object->ename b)) nil))
  )
  e
)

;; Сущность ЗАПИСИ определения? Признак один: группа 0 равна "BLOCK" --
;; у первого объекта ВНУТРИ определения она своя ("LINE", "INSERT" и
;; т. д.). Нужно потому, что группы -1 и -2 в tblsearch на живом
;; AutoCAD разные (см. KG-DefEnt): ENTD целится только в запись, обход
;; содержимого -- только от записи. Нечитаемый entget (тестовый стенд)
;; не отвергается: отвергается лишь доказанно не запись.
(defun KG-DefRecEnt (e / ed)
  (setq ed (if e (KG-Safe '(lambda () (entget e)) nil) nil))
  (or (null ed)
      (KG-StrEq (KG-AsString (cdr (assoc 0 ed))) "BLOCK"))
)

;; Жива ли прочитанная запись и носит ли она ИМЕННО это имя. Кэш KG-DefEnt
;; обязан сверять имя: переименование меняет группу 2, а ename записи
;; остаётся прежним, и устаревшая запись кэша иначе сошла бы за живую.
(defun KG-DefRecNamedP (e nm / ed)
  (setq ed (if e (KG-Safe '(lambda () (entget e)) nil) nil))
  (and ed
       (KG-StrEq (KG-AsString (cdr (assoc 0 ed))) "BLOCK")
       (KG-StrEq (KG-AsString (cdr (assoc 2 ed))) nm)
  )
)

;; Кэш «имя определения -> ename записи». АвтоЛИСП считает
;; неинициализированную переменную пустой, но стенды строже:
;; объявляем явно.
(if (not (boundp 'KG-DEFENT-CACHE)) (setq KG-DEFENT-CACHE nil))

(defun KG-DefEnt (defname / e r src nm)
  (setq nm (KG-AsString defname))
  ;; Кэш «имя -> ename»: живая очистка ищет один и тот же ename десятки
  ;; раз (проверка MINSERT, стирание, контроль после стирания), а промах
  ;; всех путей поиска стоит COM-вызова через KG-DefEntViaCom. Перебор
  ;; 56 сиротских *U в прогоне 71.4 занял 19 с, при том что каждый ename
  ;; искался по несколько раз. Запись кэша проверяется чтением с именем,
  ;; поэтому устаревшая (стёрли, переименовали) отбрасывается сама. На
  ;; стенде кэш выключен: поддельные таблицы меняются от теста к тесту.
  (if (not KG-TESTING)
    (progn
      (setq e (cdr (assoc nm KG-DEFENT-CACHE)))
      (if (not (KG-DefRecNamedP e nm)) (setq e nil))
      (if e (setq src "кэш"))
    )
  )
  (if (null e)
    (progn
  (setq e (KG-Safe '(lambda () (tblobjname "BLOCK" (KG-AsString defname)))
                   nil))
  (if (not (KG-DefRecEnt e)) (setq e nil))
  (if e (setq src "tblobjname"))
  (if (null e)
    (progn
      (setq r (KG-Call 'tblsearch (list "BLOCK" (KG-AsString defname)) nil))
      ;; Прогон сборки 50 закрыл вопрос, который две сборки оставался
      ;; гипотезой. Строка «tblsearch -> запись без -2» печаталась при
      ;; tblobjname -> nil и COM -> nil, то есть все три пути молчали, а
      ;; очистка 19 раз подряд отвечала «BLOCK не найден». Запись при этом
      ;; возвращается. Имя сущности BLOCK в ней лежит в группе -1; группа
      ;; -2 -- это ename первого объекта ВНУТРИ определения, и у пустого
      ;; или анонимного представления её может не быть вовсе. Код брал
      ;; только -2, поэтому ename не находился никогда.
      ;;
      ;; ПРОГОН СБОРКИ 71 показал последствие выбора «-2 первым»: ENTD
      ;; целился в первый вложенный примитив (стирал не блок, а его), а
      ;; обход содержимого начинался со ВТОРОГО примитива -- первая
      ;; вставка в каждом представлении не читалась, ссылки на прежние
      ;; имена не находились, и «~ИМЯ» держались невидимыми вложениями.
      ;; Теперь берётся та группа, чья сущность -- запись (группа 0
      ;; "BLOCK"): документированная -1 проверяется раньше, -2 -- после.
      (if r (setq e (cdr (assoc -1 r))))
      (if (not (KG-DefRecEnt e)) (setq e nil))
      (if e
        (setq src "tblsearch (-1)")
        (progn
          (if r (setq e (cdr (assoc -2 r))))
          (if (not (KG-DefRecEnt e)) (setq e nil))
          (if e (setq src "tblsearch (-2)"))
        )
      )
      (if (null e)
        (progn
          (setq e (KG-Safe '(lambda () (KG-DefEntViaCom defname)) nil))
          (if (not (KG-DefRecEnt e)) (setq e nil))
          (if e (setq src "COM"))
        )
      )
      (if e
        (KG-TraceDetail (strcat "BLOCK для \"" (KG-AsString defname)
                                "\" взят из " src))
        (KG-Mark (strcat "нет BLOCK для \"" (KG-AsString defname)
                         "\": tblobjname -> nil, tblsearch -> "
                         (if r "в записи нет ename примитива BLOCK" "nil")
                         ", COM -> nil"))
      )
    )
  )
      ;; Находка кладётся в кэш: KG-DefRecNamedP отбросит её сама, если
      ;; запись исчезнет или сменит имя.
      (if (and e (not KG-TESTING))
        (setq KG-DEFENT-CACHE (KG-SetAssoc nm e KG-DEFENT-CACHE))
      )
    )
  )
  e
)

;;;--- Чтение вхождений ----------------------------------------------------
;;; Вынесено ИЗ исполняющего слоя: этот цикл падал на реальном чертеже
;;; три прогона подряд, и проверять его надо на стенде. Все COM-вызовы
;;; внутри -- под перехватом, поэтому вне AutoCAD он просто отдаёт
;;; меньше данных, а не падает.

;;; Модель одного экземпляра.
;;; Каждое поле читается отдельно и со своим запасным значением: на
;;; реальном чертеже часть свойств может не читаться (анонимный
;;; динамический блок, объект внешней ссылки), и раньше любое такое поле
;;; обрывало чтение ВСЕХ вхождений -- чертёж оказывался «пустым».
;;; Метки KG-Mark называют поле: при падении команда назовёт его.
;;; Печатаются они только при (setq KG-TRACE t) -- иначе на большом
;;; чертеже командная строка переполняется и хвост отчёта теряется.
;; 72.7: нужны ли этому вхождению дорогие COM-свойства.
;; Чужая семья нужна модели только именем, слоем, точкой и масштабами;
;; её вложенная видимость и динамика не читаются вовсе.
(defun KG-InstancePropsWanted (eff)
  (and (not KG-MODEL-SKIP-PROPS)
       (or (null KG-MODEL-FAMILY)
           (KG-IsFamilyName eff KG-MODEL-FAMILY)))
)

(defun KG-InstanceModel (obj e / ed h defnm eff sp ip lay out nv kg-t0 nrm rot sx sy sz want)
  (setq ed (entget e))
  (setq h (KG-AsString (cdr (assoc 5 ed))))

  (KG-TraceDetail (strcat "вхождение " h ": имя определения"))
  (setq defnm (KG-AsString (cdr (assoc 2 ed))))

  (KG-TraceDetail (strcat "вхождение " h ": эффективное имя"))
  ;; 72.6: у анонимного представления (*U…) настоящее имя берётся из
  ;; паспорта по DXF (KG-EffNameOfEd), без COM. У обычной вставки это
  ;; группа 2.
  (setq eff (KG-EffNameOfEd ed defnm e))
  (if (= eff "") (setq eff defnm))
  ;; 72.7: решаем один раз на вхождение. Для чужой семьи дорогие
  ;; COM-вызовы не делаются; поля остаются пустыми, а имя, слой и
  ;; геометрия читаются как обычно.
  (setq want (KG-InstancePropsWanted eff))

  (KG-TraceDetail (strcat "вхождение " h ": пространство"))
  (setq sp (KG-Safe '(lambda () (KG-SpaceOf e)) nil))

  (setq kg-t0 (KG-SubT0))
  ;; 72.5: геометрия -- прямо из entget (10/50/41/42/43): те же значения,
  ;; что у COM-свойств, но без вызовов ActiveX. У вставки с нестандартной
  ;; нормалью группа 10 задана в OCS -- для неё остаётся прежний путь.
  (setq nrm (cdr (assoc 210 ed)))
  (if (and nrm (not (equal nrm (list 0.0 0.0 1.0) 0.000001)))
    (progn
      ;; InsertionPoint приходит variant'ом; (nth …) над ним даёт
      ;; «неверный тип аргумента: consp #<variant …>»
      (setq ip (KG-PointValue
                 (KG-Safe '(lambda () (vlax-get-property obj 'InsertionPoint)) nil)
                 (list 0.0 0.0 0.0)))
      (setq rot (KG-AsNum (KG-Field obj 'Rotation 0.0) 0.0))
      (setq sx (KG-AsNum (KG-Field obj 'XScaleFactor 1.0) 1.0))
      (setq sy (KG-AsNum (KG-Field obj 'YScaleFactor 1.0) 1.0))
      (setq sz (KG-AsNum (KG-Field obj 'ZScaleFactor 1.0) 1.0))
    )
    (progn
      (setq ip (KG-Safe '(lambda () (cdr (assoc 10 ed))) nil))
      (if (not (and ip (listp ip) (KG-Num (car ip))))
        (setq ip (list 0.0 0.0 0.0)))
      (setq rot (KG-AsNum (KG-Safe '(lambda () (cdr (assoc 50 ed))) 0.0) 0.0))
      (setq sx (KG-AsNum (KG-Safe '(lambda () (cdr (assoc 41 ed))) 1.0) 1.0))
      (setq sy (KG-AsNum (KG-Safe '(lambda () (cdr (assoc 42 ed))) 1.0) 1.0))
      (setq sz (KG-AsNum (KG-Safe '(lambda () (cdr (assoc 43 ed))) 1.0) 1.0))
    )
  )
  (KG-SubT1 "модель: вхождение -- геометрия" kg-t0)

  (KG-TraceDetail (strcat "вхождение " h ": слой"))
  (setq lay (KG-AsString (KG-Safe '(lambda () (cdr (assoc 8 ed))) "")))
  (if (= lay "") (setq lay "0"))

  (setq out
    (list
      (cons "handle" h)
      (cons "def" defnm)
      (cons "eff" eff)
      (cons "space" sp)
      (cons "layer" lay)
      (cons "pos" ip)
      (cons "rot" rot)
      (cons "sx" sx)
      (cons "sy" sy)
      (cons "sz" sz)
      (cons "normal" (list 0.0 0.0 1.0))
    )
  )

  (if want
    (progn
      (KG-TraceDetail (strcat "вхождение " h ": состояния вложенных блоков"))
      (setq kg-t0 (KG-SubT0))
      (setq nv (KG-Safe '(lambda () (KG-InstanceNestedVisibility obj eff)) nil))
      (KG-SubT1 "модель: вхождение -- вложенные состояния" kg-t0)
    )
    (progn
      (setq nv nil)
      (setq KG-LAST-NESTED-SRC nil)
      (KG-TraceDetail (strcat "вхождение " h
                              ": чужая семья, вложенные состояния не читаются"))
    )
  )
  (if (not nv) (setq nv nil))
  (setq out (cons (cons "nested-vis-src" (KG-AsString KG-LAST-NESTED-SRC)) out))
  ;; Число прочитанных состояний хранится рядом со списком: по одному
  ;; нулю в отчёте нельзя отличить «состояний не было» от «не
  ;; прочитались», а это два разных дефекта.
  (setq out (cons (cons "nested-vis-n" (length nv)) out))
  (setq out (cons (cons "nested-vis" nv) out))

  (if want
    (progn
      (KG-TraceDetail (strcat "вхождение " h ": динамические свойства"))
      (setq kg-t0 (KG-SubT0))
      (setq out (cons (cons "dyn-props"
                            (KG-Safe '(lambda () (KG-GetDynamicProperties obj)) nil))
                      out))
      (KG-SubT1 "модель: вхождение -- динамические свойства" kg-t0)
    )
    (progn
      (KG-TraceDetail (strcat "вхождение " h
                              ": чужая семья, динамика не читается"))
      (setq out (cons (cons "dyn-props" nil) out))
    )
  )

  (if want
    (progn
      (KG-TraceDetail (strcat "вхождение " h ": аннотативность"))
      (setq out (cons (cons "annotative"
                            (KG-Safe '(lambda () (KG-GetAnnotativeFlag obj)) nil))
                      out))
    )
    (setq out (cons (cons "annotative" nil) out))
  )

  (if want
    (progn
      (KG-TraceDetail (strcat "вхождение " h ": атрибуты"))
      (setq out (cons (cons "attrs"
                            (KG-Safe '(lambda () (KG-GetAttributeValues obj)) nil))
                      out))
    )
    (setq out (cons (cons "attrs" nil) out))
  )
  out
)

;; Все вхождения блоков во всём файле (модель + все листы + определения).
;; Возвращает список моделей экземпляров.
(defun KG-CollectInstances ( / ss i e obj m out skipped nospace iserr msg done total
                            ed defnm eff wantobj)
  (setq out nil skipped 0 nospace 0)
  (KG-TraceDetail "сбор вхождений блоков")
  (KG-TraceDetail "карта handle -> пространство")
  (setq KG-SPACE-MAP (KG-BuildSpaceMap))
  (setq ss (ssget "_X" '((0 . "INSERT"))))
  (setq total (if ss (sslength ss) 0))
  (setq done 0)
  (if ss
    (repeat (setq i (sslength ss))
      (setq e (ssname ss (setq i (1- i))))
      ;; 72.3: отметка каждые 100 вставок -- по протоколу видно, на какой
      ;; вставке оборвалось чтение (0xC0000005). 72.6: (gc) каждые 50 --
      ;; падение случалось до первой сборки мусора на 200-й.
      (setq done (1+ done))
      (if (zerop (rem done 100))
        (progn
          (KG-Mark (strcat "обход вставок: " (itoa done) " из " (itoa total)
                           ", handle "
                           (KG-AsString
                             (KG-Safe '(lambda () (cdr (assoc 5 (entget e)))) ""))))
          (if (zerop (rem done 50)) (gc))
        )
      )
      ;; entget здесь -- вне перехвата: на вхождении, которое не читается,
      ;; команда оборвалась бы ещё до того, как дошла до проверки
      ;; результата. Handle берётся под перехватом.
      (KG-TraceDetail (strcat "чтение вхождения "
                              (KG-AsString
                                (KG-Safe '(lambda () (cdr (assoc 5 (entget e))))
                                         ""))))
      ;; 72.7: в режиме семьи VLA-объект создаётся только для своей
      ;; вставки. Чужой он не нужен: её дорогие свойства не читаются, а
      ;; именно на такой вставке (handle 93173) падал крупный чертёж.
      ;; В обычном полном чтении (KG-MODEL-FAMILY = nil) поведение прежнее.
      (setq wantobj
        (cond
          ((not (null KG-MODEL-SKIP-PROPS)) nil)
          ((null KG-MODEL-FAMILY) t)
          (t
            (setq ed (KG-Safe '(lambda () (entget e)) nil))
            (if ed
              (progn
                (setq defnm (KG-AsString (cdr (assoc 2 ed))))
                (setq eff (KG-Safe '(lambda () (KG-EffNameOfEd ed defnm e)) ""))
                (if (= (KG-AsString eff) "")
                  t
                  (KG-InstancePropsWanted eff)))
              t))
        )
      )
      (setq obj (if wantobj
                  (vl-catch-all-apply '(lambda () (vlax-ename->vla-object e)))
                  nil))
      ;; Метки ПОСЛЕ каждого этапа. В прогоне сборки 48 команда упала с
      ;; «неверная функция: T», а последним напечатанным шагом был
      ;; «вхождение ...: динамические свойства» -- то есть метка, которая
      ;; ставится ДО чтения свойств. Всё, что исполняется после неё,
      ;; оказалось не покрыто метками, и место падения определить не
      ;; удалось. Теперь каждый этап назван.
      ;; KG-IsErr зовётся только под перехватом: vl-catch-all-error-p от
      ;; живого vla-объекта в AutoCAD сам бросает ошибку, а метка стоит
      ;; вне перехвата -- так приборка сама уронила бы команду.
      (KG-TraceDetail (strcat "вхождение получено как объект: "
                              (cond
                                ((null obj) "не нужен")
                                ((KG-Safe '(lambda () (KG-IsErr obj)) nil) "ОШИБКА")
                                (t "да"))))
      ;; ошибка на одном вхождении не должна обрывать обработку остальных,
      ;; но причину нужно видеть: без неё «не удалось прочитать» бесполезно
      (setq m (if (KG-IsErr obj) obj
                (vl-catch-all-apply '(lambda () (KG-InstanceModel obj e)))))
      (KG-TraceDetail (strcat "модель вхождения прочитана: "
                              (if (KG-Safe '(lambda () (KG-IsErr m)) nil)
                                "ОШИБКА"
                                (if m "да" "nil"))))
      ;; Прогон сборки 49: последняя метка -- «модель вхождения прочитана:
      ;; да», а падение -- до строки «вхождений прочитано». Между ними
      ;; шесть выражений, и ни одно по коду не может дать «неверная
      ;; функция: T». Значит, отказ даёт то, что выглядит безопасным, и
      ;; искать надо перебором: каждое выражение под своим перехватом и со
      ;; своей меткой. Побочный эффект -- отказ одного вхождения больше не
      ;; обрывает команду.
      (KG-TraceDetail "проверка результата чтения")
      ;; Проверка под перехватом: если она сама откажет, iserr останется
      ;; nil, вхождение уйдёт в «пропущено», а метка назовёт этап.
      (setq iserr (KG-Safe '(lambda () (KG-IsErr m)) nil))
      (KG-TraceDetail (strcat "проверка результата: "
                              (if iserr "ошибка" "не ошибка")))
      (if iserr
        (progn
          (KG-TraceDetail "печать предупреждения о вхождении")
          (setq msg (KG-Safe
                      '(lambda ()
                         (strcat "\nВНИМАНИЕ: вхождение "
                                 (KG-AsString (cdr (assoc 5 (entget e))))
                                 " (определение \""
                                 (KG-AsString (cdr (assoc 2 (entget e))))
                                 "\"): " (vl-catch-all-error-message m)))
                      "\nВНИМАНИЕ: вхождение не прочитано (текст причины не собрался)."))
          (princ (KG-AsString msg))
        )
      )
      (KG-TraceDetail "разбор пространства вхождения")
      (if (KG-Safe '(lambda () (KG-CdrCI "space" m)) nil)
        nil
        (setq nospace (1+ nospace)))
      (KG-TraceDetail "вхождение добавлено в список")
      (if (and m (not iserr))
        (setq out (cons m out))
        (setq skipped (1+ skipped))
      )
    )
  )
  (if (> done 0) (gc))
  ;; Прогон сборки 53 назвал место: «ВНИМАНИЕ: вхождения не прочитаны
  ;; (счёт вхождений)» при том, что все три вхождения к этому моменту были
  ;; прочитаны и добавлены в список. Отказ происходил в подсчёте -- и
  ;; уносил ВЕСЬ список: функция обрывалась, вызывающий получал nil, план
  ;; строился по пустой модели, и INTEGRATE печатала «Заменено 0» при двух
  ;; живых экземплярах в чертеже.
  ;; Подсчёт и печать теперь под перехватом, а (reverse out) -- ПОСЛЕ него:
  ;; отказ строки трассировки больше не стоит команде всех экземпляров.
  ;; Три этапа под отдельными перехватами, а не один на всё.
  ;;
  ;; Прогон сборки 58 назвал место: причина отказа -- шаг "счёт вхождений",
  ;; "неверная функция: T", а строки «вхождений прочитано: N» в логе нет
  ;; ни разу за четыре чтения модели. Значит отказ в этой группе, но из
  ;; четырёх вызовов под одним перехватом не видно, в каком именно.
  ;; Теперь каждый этап назван отдельно, и отказ одного не мешает другим.
  (setq KG-CNT-OK (KG-Safe '(lambda () (KG-TraceDetail "счёт вхождений") t) nil))
  (if (not KG-CNT-OK)
    (princ (strcat "\nВНИМАНИЕ: не поставилась метка \"счёт вхождений\" ("
                   (KG-FailText) ")."))
  )
  (setq KG-INSTCOUNT (KG-Safe '(lambda () (length out)) nil))
  (setq KG-CNT-OK
    (KG-Safe '(lambda ()
                (princ (strcat "\n[счёт] вхождений прочитано: "
                               (KG-AsString KG-INSTCOUNT)
                               (if (> skipped 0)
                                 (strcat ", пропущено из-за ошибок: "
                                         (KG-AsString skipped))
                                 "")))
                t)
              nil))
  (if (not KG-CNT-OK)
    (princ (strcat "\nВНИМАНИЕ: не напечаталось число вхождений ("
                   (KG-FailText) "), значение: "
                   (KG-AsString KG-INSTCOUNT)
                   ", пропущено: " (KG-AsString skipped) "."))
  )
  (setq KG-CNT-OK
    (KG-Safe '(lambda ()
                (if (> skipped 0)
                  (princ (strcat "\nВНИМАНИЕ: " (KG-AsString skipped)
                                 " вхождений не удалось прочитать,"
                                 " они пропущены."))
                )
                (if (> nospace 0)
                  (princ (strcat "\nВНИМАНИЕ: у " (KG-AsString nospace)
                                 " вхождений не определено пространство"
                                 " (они лежат внутри определений блоков);"
                                 " они не заменяются,"
                                 " только перепривязываются."))
                )
                t)
              nil))
  (if (not KG-CNT-OK)
    (princ (strcat "\nВНИМАНИЕ: не напечатались счётчики пропусков ("
                   (KG-FailText) "), пропущено: " (KG-AsString skipped)
                   ", без пространства: " (KG-AsString nospace) "."))
  )
  (if (KG-Safe '(lambda () (not out)) t)
    (princ "\nВНИМАНИЕ: список вхождений не читается, возвращаем пустой."))
  (KG-Safe '(lambda () (reverse out)) nil)
)

;; Вставки, которые указывают на отсутствующее определение.
;;
;; Повод -- прогон сборки 50: INTEGRATE напечатала «УСПЕШНО, замечаний
;; нет» при «Заменено экземпляров: 0», а в чертёже остались два экземпляра
;; семейства. Валидация этого не увидела, потому что искала старые
;; экземпляры ПО ИМЕНИ варианта, а определения к тому моменту были
;; переименованы и сняты. Признак такого состояния общий и проверяется без
;; знания плана: у вставки есть группа 2, а записи блока с этим именем нет.
;; Стоит функция до границы исполняющего слоя, чтобы её можно было
;; проверить на стенде.
(defun KG-DanglingInserts ( / ss i e ed nm n out)
  (setq n 0 out nil)
  (setq ss (KG-Safe '(lambda () (ssget "_X" '((0 . "INSERT")))) nil))
  (if ss
    (repeat (setq i (sslength ss))
      (setq e (ssname ss (setq i (1- i))))
      (setq ed (KG-Safe '(lambda () (entget e)) nil))
      (setq nm (if ed (KG-AsString (cdr (assoc 2 ed))) ""))
      (if (and (/= nm "")
               (not (KG-Safe '(lambda () (KG_EXDefExists nm)) nil)))
        (progn
          (setq n (1+ n))
          (if (< (length out) 10)
            (setq out (cons (strcat nm " (вставка "
                                    (KG-AsString
                                      (KG-Safe
                                        '(lambda () (cdr (assoc 5 ed))) ""))
                                    ")")
                            out)))
        )
      )
    )
  )
  (list n (reverse out))
)

;; Сколько вставок семейства стоит в чертеже и какими именами они видны.
;;
;; Повод -- прогон, в котором INTEGRATE напечатала «УСПЕШНО, замечаний
;; нет» при «Заменено экземпляров: 0». По отчёту нельзя было отличить
;; «в чертеже действительно нет экземпляров семейства» от «экземпляры
;; есть, но сканирование увидело их под другими именами». Различие
;; принципиальное: во втором случае имена экземпляров меняет наше же
;; освобождение имён до вставки, и план оказывается пустым.
;; Считает по вставкам напрямую, минуя модель и план.
(defun KG-FamilyInstances (base / ss i e ed eff out n lst)
  (setq n 0 lst nil)
  (setq ss (KG-Safe '(lambda () (ssget "_X" '((0 . "INSERT")))) nil))
  (if ss
    (repeat (setq i (sslength ss))
      (setq e (ssname ss (setq i (1- i))))
      (setq ed (KG-Safe '(lambda () (entget e)) nil))
      (setq eff "")
      (if ed
        (setq eff (KG-EffNameOfEd ed (KG-AsString (cdr (assoc 2 ed))) e)))
      (if (= eff "")
        (if ed (setq eff (KG-AsString (cdr (assoc 2 ed))))))
      (setq out (KG-Safe '(lambda () (KG-ParseBlockName eff)) nil))
      (if (and out (KG-StrEq (KG-AsString (nth 0 out))
                             (KG-AsString base)))
        (progn
          (setq n (1+ n))
          (if (not (KG-StrInterCI (list eff) lst))
            (setq lst (cons eff lst)))
        )
      )
    )
  )
  (list n (reverse lst))
)

;; Variant -> safearray, либо nil.
;;; AllowedValues у свойства без списка допустимых значений возвращает
;;; ПУСТОЙ variant (тип 8197, VT_EMPTY). Развёртывание такого значения
;;; через vlax-variant-value бросает ошибку, и именно она обрывала команду:
;;; в первом логе это было "consp #<variant 8197>".
(defun KG-VariantToArray (v / a)
  (if (or (null v) (KG-IsErr v))
    nil
    (progn
      (setq a (vl-catch-all-apply '(lambda () (vlax-variant-value v))))
      (if (KG-IsErr a)
        nil
        (if (KG-IsErr (vl-catch-all-apply
                        '(lambda () (vlax-safearray-get-u-bound a 1))))
          nil
          a))
    )
  )
)

;; Число элементов в safearray (0, если это не массив). Всегда число:
;; результат уходит в (> … 0), а там nil дал бы «fixnump: nil».
(defun KG-ArrayCount (arr / n)
  (if (null arr)
    0
    (progn
      (setq n (vl-catch-all-apply '(lambda () (vlax-safearray-get-u-bound arr 1))))
      (if (KG-Num n) (1+ n) 0)
    )
  )
)

;; Имя свойства среди динамических свойств объекта. Отдельная функция:
;; KG-FindVisibilityProperty зовётся с аргументом, и вложенная лямбда,
;; цитирующая локальную переменную вызывающей функции, подставляется
;; ненадёжно.
(defun KG-FindDynPropByName (obj want / props p nm out)
  (setq out nil)
  (setq props (vl-catch-all-apply
                '(lambda () (vlax-invoke obj 'GetDynamicBlockProperties))))
  (if (and (not (KG-IsErr props)) props)
    (foreach p props
      (if (not out)
        (progn
          (setq nm (vl-catch-all-apply '(lambda () (vla-get-PropertyName p))))
          (if (and (not (KG-IsErr nm)) (KG-StrEq nm want)) (setq out p))
        )
      )
    )
  )
  out
)

;; Свойство среди динамических свойств объекта по признакам.
(defun KG-FindDynPropBy (obj / props p nm allowed out)
  (setq out nil)
  (setq props (vl-catch-all-apply
                '(lambda () (vlax-invoke obj 'GetDynamicBlockProperties))))
  (if (and (not (KG-IsErr props)) props)
    (foreach p props
      (if (not out)
        (progn
          (setq nm (vl-catch-all-apply '(lambda () (vla-get-PropertyName p))))
          (setq allowed (vl-catch-all-apply
                          '(lambda () (vlax-get-property p 'AllowedValues))))
          ;; Параметр видимости обязан иметь список состояний; пустой
          ;; variant (VT_EMPTY) означает, что это не он. Точное имя здесь
          ;; намеренно НЕ сверяется: это задача KG-FindDynPropByName.
          ;; Пока сверялось и здесь, запасной путь подменял основной, и
          ;; «имя из словаря не используется» не меняло результата.
          (if (and (not (KG-IsErr nm))
                   (> (KG-ArrayCount (KG-VariantToArray allowed)) 0)
                   (wcmatch (strcase (KG-AsString nm)) "*ВИДИМ*,*VISIB*"))
            (setq out p)
          )
        )
      )
    )
  )
  out
)

;; Имя параметра видимости из словаря расширения определения блока.
;;
;; Это единственный способ узнать имя, не угадывая его. Параметр видимости
;; хранится в ACAD_ENHANCEDBLOCK расширения записи блока как сущность
;; BLOCKVISIBILITYPARAMETER, а его имя -- в группе 301.
;;
;; Почему это понадобилось. Параметр искали по написанию имени --
;; «*ВИДИМ*» или «*VISIB*». Прогон сборки 63 показал: у вложенных блоков
;; определений «Стойка КП50» и «Стойка КП50 контур» читается ноль состояний
;; при четырёх и шести вложенных вставках, а у «Закладная в полость стойки»
;; состояния есть. Значит, у части блоков параметр назван иначе, и поиск по
;; имени его не находил -- состояния не снимались и вернуть их было нечего.
;; Пользователь видел ровно это: «состояние сброшено на базовую видимость».
(defun KG-VisParamName (obj / eff blk d e ed rec out x)
  (setq out nil)
  ;; 72.6: имя вставки -- из паспорта (DXF), BLOCK_RECORD -- по группе 330
  ;; примитива BLOCK. Раньше на каждое чтение состояния шли три COM-вызова:
  ;; EffectiveName, vla-Item и vla-object->ename. Словарь ACAD_ENHANCEDBLOCK
  ;; ищется у той же записи BLOCK_RECORD, что возвращал vla-object->ename.
  (setq e (KG-Safe '(lambda () (vlax-vla-object->ename obj)) nil))
  (setq ed (if e (KG-Safe '(lambda () (entget e)) nil) nil))
  (if ed
    (setq eff (KG-EffNameOfEd ed (KG-AsString (cdr (assoc 2 ed))) e))
    (setq eff (KG-EffectiveNameOf obj))
  )
  (setq e (if (and eff (/= eff ""))
            (KG-Safe '(lambda () (KG-DefEnt eff)) nil)
            nil))
  (setq ed (if e (KG-Safe '(lambda () (entget e)) nil) nil))
  (setq rec (if ed (cdr (assoc 330 ed)) nil))
  (setq d nil)
  (if rec
    (setq d (KG-Safe '(lambda ()
                        (dictsearch (entget rec) "ACAD_ENHANCEDBLOCK"))
                     nil))
    ;; Запасной путь: та же запись BLOCK_RECORD через COM. Нужен, когда
    ;; KG-DefEnt не нашёл примитив BLOCK (сиротское имя, стенд).
    (progn
      (setq blk (if (and eff (/= eff ""))
                  (KG-Safe '(lambda () (KG-BlockObj eff)) nil)
                  nil))
      (if (and blk (not (KG-IsErr blk)))
        (progn
          (setq e (KG-Safe '(lambda () (vlax-vla-object->ename blk)) nil))
          (if (and e (not (KG-IsErr e)))
            (setq d (KG-Safe '(lambda ()
                                (dictsearch (entget e) "ACAD_ENHANCEDBLOCK"))
                             nil))
          )
        )
      )
    )
  )
  (if d
    (progn
      (setq e (cdr (assoc 360 d)))
      (if e
        (progn
          (setq ed (KG-Safe '(lambda () (entget e)) nil))
          (foreach x ed
            (if (and (not out) (KG-StrEq (car x) 301))
              (setq out (KG-AsString (cdr x)))
            )
          )
        )
      )
    )
  )
  (if (and out (/= out "")) out nil)
)

;; Параметр видимости объекта.
;;
;; Порядок поиска: точное имя из словаря определения, затем прежнее
;; распознавание по написанию имени. Первый способ основной: он не зависит от
;; того, как параметр назвали. Второй оставлен запасным -- на случай, когда
;; словарь не читается.
;;
;; Третий аргумент -- куда записать, каким способом параметр найден:
;; "имя" или "написание". Без этого по отчёту не отличить «параметр не найден»
;; от «найден запасным путём».
(defun KG-FindVisibilityProperty (obj want how / p)
  (setq p nil)
  (if want (setq p (KG-FindDynPropByName obj want)))
  (if (and p how) (setq how "имя"))
  (if (null p)
    (progn
      (setq p (KG-FindDynPropBy obj))
      (if (and p how) (setq how "написание"))
    )
  )
  p
)

;; Параметр видимости: имя берётся из словаря определения.
(defun KG-VisibilityPropertyOf (obj / want)
  (setq want (KG-Safe '(lambda () (KG-VisParamName obj)) nil))
  (KG-FindVisibilityProperty obj want nil)
)

;; Список допустимых состояний видимости экземпляра
(defun KG-GetAllowedVisibilityStates (obj / p arr i n out)
  (setq out nil)
  (setq p (KG-VisibilityPropertyOf obj))
  (if p
    (progn
      (setq arr (KG-VariantToArray
                  (vl-catch-all-apply '(lambda () (vlax-get-property p 'AllowedValues)))))
      (if arr
        (progn
          (setq n (1- (KG-ArrayCount arr)))
          (setq i 0)
          (while (<= i n)
            (setq out (cons (KG-AsString
                              (vl-catch-all-apply
                                '(lambda ()
                                   (vlax-variant-value
                                     (vlax-safearray-get-element arr i)))))
                            out))
            (setq i (1+ i))
          )
        )
      )
    )
  )
  (reverse out)
)

;; Текущее состояние видимости экземпляра. Всегда строка или nil.
;; Значение параметра приходит variant'ом (VT_BSTR): на реальном чертеже
;; в предупреждениях печаталось «#<variant 8 КП45303 70/45>» вместо имени
;; состояния, а сравнение со списком допустимых состояний такой пары не
;; находило -- состояние считалось отсутствующим в новой версии.
(defun KG-GetVisibilityState (obj / p v sv)
  (setq p (KG-VisibilityPropertyOf obj))
  (if p
    (progn
      (setq v (vl-catch-all-apply '(lambda () (vlax-get-property p 'Value))))
      (if (KG-IsErr v)
        nil
        (progn
          (setq sv (vl-catch-all-apply '(lambda () (vlax-variant-value v))))
          (if (KG-IsErr sv) (KG-AsString v) (KG-AsString sv))
        )
      )
    )
    nil
  )
)

;; Установить состояние видимости
(defun KG-SetVisibilityState (obj val / p r vval)
  (setq p (KG-VisibilityPropertyOf obj))
  (if p
    (progn
      (setq vval (vl-catch-all-apply '(lambda () (vlax-variant-value val))))
      (if (or (KG-IsErr vval) (null vval)) (setq vval val))
      ;; Параметр видимости всегда строковый: передаём variant vbString
      (setq r (vl-catch-all-apply
                '(lambda ()
                   (vlax-put-property p 'Value (vlax-make-variant (KG-AsString vval) vlax-vbString)))))
      (if (KG-IsErr r)
        (setq r (vl-catch-all-apply
                  '(lambda ()
                     (vlax-put p 'Value (KG-AsString vval)))))
      )
      (if (KG-IsErr r)
        (setq r (vl-catch-all-apply
                  '(lambda ()
                     (vlax-put-property p 'Value val))))
      )
      (if (KG-IsErr r)
        (setq r (vl-catch-all-apply
                  '(lambda ()
                     (vlax-put-property p 'Value vval))))
      )
      (not (KG-IsErr r))
    )
    nil
  )
)


;;;--- Служебные объекты COM -------------------------------------------------

(defun KG-Acad ( / *acad*)
  (setq *acad* (vlax-get-acad-object))
)
(defun KG-Doc () (vla-get-ActiveDocument (KG-Acad)))
(defun KG-Model ( / d) (setq d (KG-Doc)) (vla-get-ModelSpace d))
(defun KG-Blocks () (vla-get-Blocks (KG-Doc)))

;; Объект-определение по имени, nil если нет
(defun KG-BlockObj (name)
  (vl-catch-all-apply
    '(lambda () (vla-Item (KG-Blocks) name)))
)

;; Имя листа по имени блока *Paper_Space*
;; Ищется лист, чей блок носит это имя; возвращается ИМЯ ЛИСТА.
;; Раньше имя листа сравнивалось с самим собой и функция возвращала
;; имя блока: запасной путь KG-SpaceOf отдавал "*Paper_Space" вместо
;; "Лист1", а KG_EXCreateInstance по такому имени не находил лист и
;; уводил новый экземпляр в МОДЕЛЬ (живой прогон, 17.10). Не найдено --
;; nil: «не удалось определить» (см. KG-SpaceOf).
(defun KG-LayoutNameFor (blockname / lays lay res blk bnm)
  (setq res nil)
  (setq lays (vl-catch-all-apply '(lambda () (vla-get-Layouts (KG-Doc)))))
  (if (not (KG-IsErr lays))
    (vlax-for lay lays
      (if (null res)
        (progn
          (setq blk (vl-catch-all-apply '(lambda () (vla-get-Block lay))))
          (setq bnm
            (if (or (KG-IsErr blk) (null blk))
              nil
              (vl-catch-all-apply '(lambda () (vla-get-Name blk)))
            )
          )
          (if (and bnm (not (KG-IsErr bnm)) (KG-StrEq bnm blockname))
            (setq res (vl-catch-all-apply '(lambda () (vla-get-Name lay))))
          )
        )
      )
    )
  )
  (if (KG-IsErr res) nil res)
)

;;;--- Пространство экземпляра -----------------------------------------------
;;;
;;; Группа 330 (handle владельца) в entget экземпляра есть НЕ во всех
;;; файлах: на реальном чертеже (прогон FINDBUG, 18.09) её не оказалось
;;; ни у одного INSERT, поэтому handent получал nil и падал на каждом
;;; вхождении -- чертеж читался как пустой («прочитано: 0, с ошибками: 3»).
;;;
;;; Рабочий путь: пройти таблицу блоков и для модели и каждого листа
;;; спросить у пространства handle каждого лежащего в нём объекта
;;; (vla-get-Handle). Карта строится один раз за команду.
;;; Группа 330 остаётся запасным вариантом.

;; Пространство экземпляра: "Model" или имя листа.
;;; Принимает ename. nil означает «не удалось определить» -- вызывающий
;;; обязан это обработать, а не считать пространством модель.
(defun KG-SpaceOf (e / h sp)
  (setq h (KG-HandleOf e))
  (setq sp (if h (KG-SpaceOfHandle h) nil))
  (cond
    (sp sp)
    (h (progn
         (setq sp (KG-OwnerBlockName e))
         (cond
           ((null sp) nil)
           ((KG-StrEq sp "*Model_Space") "Model")
           (t (KG-LayoutNameFor sp)))))
    (t nil)
  )
)

;; Handle объекта как строка (группа 5)
(defun KG-HandleOf (e / ed)
  (if (or (null e) (= (type e) (type "")))
    nil
    (progn
      (setq ed (entget e))
      (if ed (KG-AsString (cdr (assoc 5 ed))) nil)
    )
  )
)

;; Handle -> имя пространства по построенной карте, nil если handle не найден
(defun KG-SpaceOfHandle (handle / h p)
  (setq h (strcase (KG-AsString handle)))
  (setq p (assoc h KG-SPACE-MAP))
  (if p (cdr p) nil)
)

;; Карта handle -> имя пространства для модели и всех листов
(defun KG-BuildSpaceMap ( / blocks blk nm sp lay map n)
  (setq map nil n 0)
  (setq blocks (vl-catch-all-apply '(lambda () (KG-Blocks))))
  (if (not (KG-IsErr blocks))
    (vlax-for blk blocks
      (setq nm (vl-catch-all-apply '(lambda () (vla-get-Name blk))))
      (if (and (not (KG-IsErr nm))
               (not (KG-ComBool
                      (vl-catch-all-apply '(lambda () (vla-get-IsXRef blk))))))
        (progn
          (setq sp
            (cond
              ((wcmatch (strcase (KG-AsString nm)) "`*MODEL_SPACE*") "Model")
              ((wcmatch (strcase (KG-AsString nm)) "`*PAPER_SPACE*")
               (setq lay (vl-catch-all-apply '(lambda () (vla-get-Layout blk))))
               (if (or (KG-IsErr lay) (null lay))
                 ;; имя блока в карту не пишется: потребители принимают
                 ;; значение карты за имя листа и уводят объект в МОДЕЛЬ
                 nil
                 (progn
                   (setq nm (vl-catch-all-apply '(lambda () (vla-get-Name lay))))
                   (if (KG-IsErr nm) nil (KG-AsString nm)))))
              (t nil)))
          (if sp
            (progn
              (setq n (1+ n))
              (setq map (KG-MapSpaceEntities blk sp map))
            )
          )
        )
      )
    )
  )
  ;; обход таблицы блоков может не дать ничего (на реальном чертеже так и
  ;; вышло: «объектов в карте пространств: 0»). Тогда пространства
  ;; берутся из коллекции Layouts -- это второй, независимый путь.
  (if (null map)
    (progn
      (KG-Mark "карта по таблице блоков пуста, обход через Layouts")
      (setq map (KG-BuildSpaceMapByLayouts))
    )
  )
  (KG-TraceDetail (strcat "карта пространств: " (itoa (length map))
                    " объектов, пространств пройдено: " (itoa n)))
  (reverse map)
)

;; Запасной путь: пространства из коллекции Layouts
(defun KG-BuildSpaceMapByLayouts ( / lays lay nm blk map)
  (setq map nil)
  (setq lays (vl-catch-all-apply '(lambda () (vla-get-Layouts (KG-Doc)))))
  (if (not (KG-IsErr lays))
    (vlax-for lay lays
      (setq nm (vl-catch-all-apply '(lambda () (vla-get-Name lay))))
      (setq blk (vl-catch-all-apply '(lambda () (vla-get-Block lay))))
      (if (and (not (KG-IsErr nm)) nm (not (KG-IsErr blk)) blk)
        (setq map (KG-MapSpaceEntities blk (KG-AsString nm) map))
      )
    )
  )
  map
)

;; Дописать в карту handle всех объектов пространства blk
(defun KG-MapSpaceEntities (blk sp map / h)
  (vl-catch-all-apply
    '(lambda ()
       (vlax-for e blk
         (setq h (vl-catch-all-apply '(lambda () (vla-get-Handle e))))
         (if (and (not (KG-IsErr h)) h)
           (setq map (cons (cons (strcase (KG-AsString h)) sp) map))
         )
       )))
  map
)

;; Перестроить карту handle -> пространство (после вставки из буфера)
(defun KG-RefreshSpaceMap ()
  (setq KG-SPACE-MAP (KG-BuildSpaceMap))
)

;; Имя блока-владельца экземпляра через группу 330 (запасной путь)
(defun KG-GetDynamicProperties (obj / props p nm val out)
  (setq out nil)
  ;; Никаких предварительных проверок доступности.
  ;;
  ;; vlax-property-available-p проверяет СВОЙСТВА, а
  ;; GetDynamicBlockProperties -- МЕТОД: проверка всегда возвращала nil,
  ;; условие (and ...) не выполнялось, и у каждого экземпляра читался
  ;; пустой список свойств. Отчёт печатал «Прочитано свойств у старых
  ;; экземпляров: 0», и состояния видимости не переносились.
  ;; Правильной была бы vlax-method-applicable-p, но проще и надёжнее
  ;; сразу вызвать метод под перехватом: у статического блока он
  ;; откажет, и список останется пустым.
  (if obj
    (progn
      (setq props (vl-catch-all-apply
                    '(lambda () (vlax-invoke obj 'GetDynamicBlockProperties))))
      (if (and (not (KG-IsErr props)) props)
        (foreach p props
          (setq nm (vl-catch-all-apply '(lambda () (vla-get-PropertyName p))))
          (setq val (vl-catch-all-apply '(lambda () (vlax-get-property p 'Value))))
          (if (and (not (KG-IsErr nm)) (not (KG-IsErr val)))
            (setq out (cons (cons nm val) out))
          )
        )
      )
    )
  )
  (reverse out)
)

;;; Чтение значений атрибутов вхождения блока (ATTRIB).
;;; Возвращает ассоциативный список (("ТЕГ" . "ЗНАЧЕНИЕ") ...).
(defun KG-GetAttributeValues (obj / attrs a tag val out)
  (setq out nil)
  (if obj
    (progn
      (setq attrs (vl-catch-all-apply '(lambda () (vlax-invoke obj 'GetAttributes))))
      (if (and (not (KG-IsErr attrs)) attrs)
        (foreach a attrs
          (setq tag (vl-catch-all-apply '(lambda () (vla-get-TagString a))))
          (setq val (vl-catch-all-apply '(lambda () (vla-get-TextString a))))
          (if (and (not (KG-IsErr tag)) (not (KG-IsErr val)))
            (setq out (cons (cons (KG-AsString tag) (KG-AsString val)) out))
          )
        )
      )
    )
  )
  (reverse out)
)

;;; Запись значений атрибутов во вхождение блока.
;;; Сопоставление тегов регистронезависимое через KG-CdrCI.
;;; Возвращает количество успешно записанных атрибутов.
(defun KG-SetAttributeValues (obj attrs / attrs-obj a tag val n)
  (setq n 0)
  (if (and obj attrs)
    (progn
      (setq attrs-obj (vl-catch-all-apply '(lambda () (vlax-invoke obj 'GetAttributes))))
      (if (and (not (KG-IsErr attrs-obj)) attrs-obj)
        (foreach a attrs-obj
          (setq tag (vl-catch-all-apply '(lambda () (vla-get-TagString a))))
          (if (not (KG-IsErr tag))
            (progn
              (setq val (KG-CdrCI (KG-AsString tag) attrs))
              (if val
                (if (not (KG-IsErr (vl-catch-all-apply
                                     '(lambda () (vla-put-TextString a (KG-AsString val))))))
                  (setq n (1+ n))
                )
              )
            )
          )
        )
      )
    )
  )
  n
)

;;; Чтение флага аннотативности вхождения.
(defun KG-GetAnnotativeFlag (obj / r)
  (if (and obj (vlax-property-available-p obj 'Annotative))
    (progn
      (setq r (vl-catch-all-apply '(lambda () (vla-get-Annotative obj))))
      (if (and (not (KG-IsErr r)) (= r :vlax-true))
        t
        nil
      )
    )
    nil
  )
)

;; Эвристика поиска параметра видимости (п. 9.5 ТЗ).
;; Признаки: имя содержит "видим"/"visib", есть список допустимых значений,
;; свойство доступно для записи.
;









;; Состояния видимости вложенных динамических блоков внутри определения
(defun KG-DefNestedVisibility (defname / blk out ent eo)
  (setq out nil)
  (setq blk (KG-BlockObj defname))
  (if (and blk (not (KG-IsErr blk)))
    (vlax-for e blk
      (if (= (vla-get-ObjectName e) "AcDbBlockReference")
        (progn
          (setq eo e)
          (setq out
            (cons (cons (KG-EffectiveNameOf eo)
                        (KG-GetVisibilityState eo))
                  out))
        )
      )
    )
  )
  (reverse out)
)

;;;--- Адаптер чтения: построение модели чертежа -----------------------------

(defun KG_DBGetModel ( / defs insts lays blk e defs-l insts-l nm d err)
  ;; 71.9: кэш состояний вложенных вставок живёт одно чтение модели: между
  ;; чтениями чертёж меняют (подмена определений, перепривязка), и старый
  ;; ответ был бы про прежнее содержимое.
  (setq KG-SCAN-CACHE nil)
  (KG-TraceDetail "чтение таблицы блоков")
  (setq defs-l nil)
  ;; список пропущенных сбрасывается на каждый прогон: иначе имена
  ;; прошлого отказа висели бы в отчёте следующего.
  (setq KG-SKIP-DEFS nil)
  (vlax-for blk (KG-Blocks)
    (setq nm (vl-catch-all-apply '(lambda () (vla-get-Name blk))))
    ;; Проверка результата тоже перехвачена: (vl-catch-all-error-p) от
    ;; неожиданного значения сам бросает «неверная функция: T», и тогда
    ;; метка «чтение определения» уже напечатана, а причина осталась бы
    ;; за пределами перехвата свойств ниже.
    (if (not (KG-IsErrSafe nm t))
      (progn
        (KG-TraceDetail (strcat "чтение определения \""
                                (KG-AsString nm) "\""))
        ;; Определение может не читаться: анонимный динамический блок,
        ;; внешняя ссылка, определение, которое ActiveX отдаёт с
        ;; ошибкой. Отказ ОДНОГО определения не обязан обрывать всю
        ;; команду. Прогон сборки 55: снимок не прочитан на "*U54",
        ;; а второй снимок оборвал INTEGRATE целиком на "*U87" --
        ;; «неверная функция: T», уже после вставки из буфера.
        ;; Теперь определение пропускается, причина печатается, а
        ;; модель собирается из остальных.
        (setq d (vl-catch-all-apply
                  '(lambda ()
                     (list
                       (cons "name" nm)
                       (cons "is-xref"
                             ;; 72.5: флаги записи блока (группа 70) --
                             ;; один entget вместо COM-запроса.
                             (KG-DefIsXRefP nm))
                       (cons "is-layout"
                             (if (wcmatch (strcase (KG-AsString nm))
                                          "`*MODEL_SPACE,`*PAPER_SPACE*")
                               t nil))
                       ;; 72.5: поле в модели никем не читается,
                       ;; COM-запрос по каждому определению убран.
                       (cons "is-dynamic" nil)
                       (cons "nested" (KG-DefNestedRefs nm))
                       (cons "vis-states" (KG-DefVisStates nm))
                       (cons "vis-param" nil)
                     ))))
        (if (KG-IsErrSafe d t)
          (progn
            ;; имя отказа обязательно: без него «пропущено»
            ;; неотличимо от «определения не было»
            (setq err (KG-AsString
                        (vl-catch-all-apply
                          '(lambda () (vl-catch-all-error-message d)))))
            (setq KG-SKIP-DEFS (cons (KG-AsString nm) KG-SKIP-DEFS))
            (princ (strcat "\nВНИМАНИЕ: определение \""
                           (KG-AsString nm) "\" не прочитано ("
                           err ") -- пропущено, обработка продолжается."))
          )
          (if d (setq defs-l (cons d defs-l)))
        )
      )
    )
  )
  ;; Метка ПОСЛЕ цикла: по ней видно, дочитан ли список определений.
  ;; Без неё «чтение определения "X"» оставалась последней меткой и
  ;; при отказе в самом обходе коллекции -- то есть указывала не туда.
  (KG-TraceDetail "таблица блоков прочитана")
  ;; Счётчик прочитанных определений -- и заодно диагностика.
  ;;
  ;; Прогон сборки 57: интеграция прошла полностью, но шесть раз
  ;; напечаталось «не напечаталось число определений (шаг "таблица
  ;; блоков прочитана", неверная функция: T)». Строка состояла из
  ;; четырёх вызовов под одним перехватом, и какой из них отказал --
  ;; видно не было. Теперь вызов один, а печатается сырое значение:
  ;; отказ печати отделён от отказа подсчёта, и предупреждение называет
  ;; значение, на котором случилось.
  (setq KG-DEFCOUNT (KG-Safe '(lambda () (length defs-l)) nil))
  (setq KG-CNT-OK (KG-Safe '(lambda ()
                              (princ (strcat "\n[счёт] определений в списке: "
                                             (KG-AsString KG-DEFCOUNT)))
                              t)
                            nil))
  (if (not KG-CNT-OK)
    (princ (strcat "\nВНИМАНИЕ: не напечаталось число определений ("
                   (KG-FailText) "), значение: "
                   (KG-AsString KG-DEFCOUNT) "."))
  )
  (if KG-SKIP-DEFS
    (if (not (KG-Safe '(lambda ()
                        (KG-Say (strcat
                          "Определений не прочитано и пропущено: "
                          (KG-NumStr (length KG-SKIP-DEFS))))
                        (KG-SayList (reverse KG-SKIP-DEFS) 10)
                        t)
                      nil))
      (princ (strcat "\nВНИМАНИЕ: не напечатался список пропущенных ("
                     (KG-FailText) ")."))
    )
  )
  ;; Сбор вхождений может не дочитаться (прогон сборки 49). Лучше
  ;; INTEGRATE продолжится с неполными данными и назовёт причину, чем
  ;; оборвётся посередине, оставив имена освобождёнными.
  (KG-TraceDetail "сбор вхождений")
  (setq insts-l (KG-Safe '(lambda () (KG-CollectInstances)) nil))
  (if (and (null insts-l) KG-FAIL-STEP)
    (princ (strcat "\nВНИМАНИЕ: вхождения не прочитаны ("
                   (KG-FailText)
                   "). Интеграция продолжена без них.")))
  ;; Модель возвращается ВСЕГДА. Пустая модель -- неполный отчёт,
  ;; отсутствующая модель -- «мастер-версия не найдена» при живом блоке.
  (list
    (cons "defs" (KG-Safe '(lambda () (reverse defs-l)) nil))
    (cons "insts" insts-l)
    (cons "layouts" nil)
  )
)

;; Внешняя ссылка по флагам записи блока (группа 70): 4 -- ссылка,
;; 8 -- наложенная ссылка. Зависимые от ссылки определения (16)
;; внешними ссылками не считаются -- как и свойство IsXRef.
(defun KG-DefIsXRefP (defname / e ed fl)
  (setq e (KG-Safe '(lambda () (KG-DefEnt defname)) nil))
  (setq ed (if e (KG-Safe '(lambda () (entget e)) nil) nil))
  (setq fl (if ed (cdr (assoc 70 ed)) 0))
  ;; Разбор битов перехвачен: испорченная запись (или стенд без
  ;; logand) не должна уносить чтение модели -- в худшем случае
  ;; определение не будет сочтено внешней ссылкой.
  (setq fl (KG-Safe '(lambda () (logand fl 12)) nil))
  (if (and (KG-Num fl) (/= fl 0)) t nil)
)

;; Снимок только вхождений. Шагу перепривязки вложенных вхождений
;; определения не нужны, а их чтение -- самая дорогая часть снимка.
(defun KG-DBGetInstancesOnly ( / insts-l)
  (setq KG-SCAN-CACHE nil)
  (setq insts-l (KG-Safe '(lambda () (KG-CollectInstances)) nil))
  (list
    (cons "defs" nil)
    (cons "insts" insts-l)
    (cons "layouts" nil)
  )
)

;; Вложенные имена определений внутри определения defname.
;;
;; 72.5: обход содержимого -- по DXF (entnext/entget), а не vlax-for с
;; vla-get-ObjectName: на крупном чертеже это десятки тысяч вызовов
;; ActiveX на одно чтение модели. 72.6: эффективное имя *U-вставки тоже
;; берётся из паспорта по DXF -- COM в обходе определений больше нет.
(defun KG-DefNestedRefs (defname / e ed out nm obj r)
  (setq out nil)
  (setq e (KG-Safe '(lambda () (KG-DefEnt defname)) nil))
  ;; Обход содержания перехвачен целиком: отказ на одном вложенном
  ;; объекте отдаёт уже найденное, а не уносит всю функцию.
  (setq r (vl-catch-all-apply
            '(lambda ()
               (while (and e
                           (setq e (entnext e))
                           (setq ed (entget e))
                           (/= (KG-AsString (cdr (assoc 0 ed))) "ENDBLK"))
                 (if (KG-StrEq (KG-AsString (cdr (assoc 0 ed))) "INSERT")
                   (progn
                     ;; 72.6: имя -- из паспорта по DXF, без COM.
                     (setq nm (KG-EffNameOfEd ed (KG-AsString (cdr (assoc 2 ed))) e))
                     (if (and nm (/= nm "") (not (member nm out)))
                       (setq out (cons nm out))
                     )
                   )
                 )
               )
               out)))
  (if (KG-IsErr r) nil (reverse out))
)

;; Допустимые состояния видимости самого определения (через любое вхождение)
(defun KG-DefVisStates (defname / ss i e obj out r)
  (setq out nil)
  ;; Отказ чтения состояний -- не отказ всего определения: ssget,
  ;; ssname и vlax-ename->vla-object на анонимном представлении могут
  ;; не отдать ничего, и раньше это уносило вызывающую функцию.
  (setq r (vl-catch-all-apply
            '(lambda ()
               (setq ss (ssget "_X" (list '(0 . "INSERT")
                                          (cons 2 defname))))
               (if (and ss (> (sslength ss) 0))
                 (progn
                   (setq e (ssname ss 0))
                   (setq obj (vlax-ename->vla-object e))
                   (setq out (KG-GetAllowedVisibilityStates obj))
                 )
               ))))
  (if (KG-IsErr r) nil out)
)
;;
;; Возвращает список ((имя-вложенного . состояние) ...), а состояние
;; представления -- в KG-LAST-NESTED-SRC: "*U" (прочитано у анонимного
;; представления экземпляра), "ОПРЕДЕЛЕНИЕ" (представления нет,
;; прочитаны состояния по умолчанию из родительского определения) или
;; "НЕТ" (ни там, ни там вложенных вставок не найдено).
;;
;; Почему нужен второй путь: на реальном чертеже вставка может указывать
;; не на *U, а прямо на определение -- тогда её вложенные блоки стоят в
;; состояниях по умолчанию, и эти состояния лежат в определении. Без
;; запасного пути отчёт печатал «Прочитано состояний вложенных блоков:
;; 0», и отличить «состояний не было» от «не там искали» было нельзя.
(defun KG-InstanceNestedVisibility (obj eff / out en ed def e sub nm v)
  (setq out nil)
  (setq KG-LAST-NESTED-SRC "НЕТ")
  (setq en (KG-Safe '(lambda () (vlax-vla-object->ename obj)) nil))
  (if en
    (progn
      (setq def (KG_DefNameOfEnt en))
      ;; 72.6: вызывающий уже прочитал имя по паспорту (DXF). Одиночные
      ;; вызовы (RDBDIAG) передают nil -- читаем тем же путём.
      (if (null eff)
        (setq eff (KG-EffNameOfEnt en))
      )
      (setq eff (KG-AsString eff))
      (KG-TraceDetail (strcat "вложенные состояния: вставка указывает на \""
                       def "\", эффективное имя \"" eff "\""))
      (if (KG-IsAnonDynName def)
        (progn
          (setq out (KG_ScanDefInsertStates def))
          (if out (setq KG-LAST-NESTED-SRC "*U"))
        )
        ;; представления нет: состояния вложенных блоков этого экземпляра
        ;; равны состояниям по умолчанию в родительском определении
        (progn
          (KG-TraceDetail (strcat "вложенные состояния: представления нет, читаю "
                           "определение \"" eff "\""))
          (if (/= eff "")
            (progn
              (setq out (KG_ScanDefInsertStates eff))
              (if out (setq KG-LAST-NESTED-SRC "ОПРЕДЕЛЕНИЕ"))
            )
          )
        )
      )
    )
  )
  (reverse out)
)

;; Состояния видимости вложенных вставок внутри определения. Обход только
;; через entget: COM-обход содержимого определений на реальном чертеже
;; дал 0xC0000005.
;;
;; 71.9. Три защиты от того же падения:
;;   * результат кэшируется по имени определения (KG-SCAN-CACHE): на крупном
;;     чертеже сотни экземпляров указывают на одно представление *U, и
;;     каждый сканировал его заново -- падение случилось на четвёртом скане
;;     одного и того же *U277. Запись кэша -- пара (имя . состояния);
;;     отсутствие пары означает «ещё не сканировали», а пустой ответ тоже
;;     запоминается: «вложенных состояний нет» -- это тоже ответ, и повторно
;;     в определение не лезем;
;;   * вложенные вставки со служебным именем "~..." пропускаются без
;;     COM-чтения: их состояния никому не нужны, а именно на такой вставке
;;     («~Резина ригельная ТПУ-6001») чтение свойств и упало;
;;   * KG-NESTED-COM = nil полностью отключает COM-чтение (аварийный обход
;;     для проблемного чертежа).
(defun KG_ScanDefInsertStates (defname / e ed sub nm v out cnt key hit)
  (setq out nil cnt 0)
  (setq key (KG-AsString defname))
  (setq hit (KG-AssocCI key KG-SCAN-CACHE))
  (cond
    ((or (not (boundp 'KG-NESTED-COM)) (not KG-NESTED-COM)) nil)
    (hit (cdr hit))
    (t
      ;; через KG-DefEnt: tblobjname на сиротских *U отвечает nil
      (setq e (KG-Safe '(lambda () (KG-DefEnt defname)) nil))
      (if e
        (while (and (setq e (KG-Safe '(lambda () (entnext e)) nil))
                    (setq ed (KG-Call 'entget (list e) nil))
                    (/= (KG-AsString (cdr (assoc 0 ed))) "ENDBLK"))
          (if (KG-StrEq (KG-AsString (cdr (assoc 0 ed))) "INSERT")
            (progn
              (setq cnt (1+ cnt))
              (if (KG-IsTempDefName (KG-AsString (cdr (assoc 2 ed))))
                (KG-TraceDetail (strcat "вложенная вставка \""
                                        (KG-AsString (cdr (assoc 2 ed)))
                                        "\" -- служебная, пропуск"))
                (progn
                  (KG-TraceDetail (strcat "вложенная вставка \""
                                          (KG-AsString (cdr (assoc 2 ed))) "\""))
                  (setq sub (KG-Safe '(lambda () (vlax-ename->vla-object e)) nil))
                  (if sub
                    (progn
                      ;; 72.6: имя -- из паспорта (DXF); COM остаётся
                      ;; только на само состояние видимости.
                      (setq nm (KG-EffNameOfEd ed (KG-AsString (cdr (assoc 2 ed))) e))
                      (setq v (KG-Safe '(lambda () (KG-GetVisibilityState sub)) nil))
                      (if (and nm v) (setq out (cons (cons nm v) out)))
                    )
                  )
                )
              )
            )
          )
        )
      )
      (setq out (reverse out))
      (KG-TraceDetail (strcat "в определении \"" key
                       "\" вложенных вставок: " (itoa cnt)
                       ", состояний прочитано: " (itoa (length out))))
      (setq KG-SCAN-CACHE (cons (cons key out) KG-SCAN-CACHE))
      out
    )
  )
)

;;;--- Адаптер исполнения ----------------------------------------------------

;; Handle определения блока. Нужен, чтобы отличить «AutoCAD подставил
;; старое определение» от «определение пришло из буфера»: у пришедшего
;; определения handle другой, даже если имя совпало.
(defun KG_EXDefHandle (defname / blk h)
  (setq blk (KG-BlockObj defname))
  (if (and blk (not (KG-IsErr blk)))
    (progn
      (setq h (vl-catch-all-apply '(lambda () (vla-get-Handle blk))))
      (if (KG-IsErr h) nil (KG-AsString h))
    )
    nil
  )
)

;; Снимок имён определений вместе с их handle: список пар (имя . handle)
(defun KG_EXDefHandleSnapshot ( / out)
  (setq out nil)
  (foreach nm (KG_EXAllDefNames)
    (setq out (cons (cons nm (KG_EXDefHandle nm)) out))
  )
  (reverse out)
)

;; Имена определений, которые пришли из буфера: новых имён нет в снимке,
;; а у прежних имён сменился handle. Сравнение только по именам однажды
;; уже дало ложный ответ на реальном чертеже.
(defun KG-ArrivedByHandle (snap / out nm pair)
  (setq out nil)
  (foreach nm (KG_EXAllDefNames)
    (setq pair (KG-AssocCI nm snap))
    (if (or (null pair) (not (KG-StrEq (cdr pair) (KG_EXDefHandle nm))))
      (setq out (cons nm out))
    )
  )
  (reverse out)
)

(defun KG_EXAllDefNames ( / out nm)
  (setq out nil)
  (vlax-for blk (KG-Blocks)
    (setq nm (vl-catch-all-apply '(lambda () (vla-get-Name blk))))
    (if (and (not (KG-IsErr nm)) (= (type nm) (type "")))
      (setq out (cons nm out))
    )
  )
  (reverse out)
)

(defun KG_EXDefExists (name / b)
  (setq b (KG-BlockObj name))
  (and b (not (KG-IsErr b)))
)

(defun KG_EXRenameDef (oldname newname / b r)
  (setq b (KG-BlockObj oldname))
  (if (or (not b) (KG-IsErr b))
    nil
    (progn
      (setq r (vl-catch-all-apply '(lambda () (vla-put-Name b newname))))
      (not (KG-IsErr r))
    )
  )
)

(defun KG-EXDefIsDynamic (name / b r)
  (setq b (KG-BlockObj name))
  (if (or (not b) (KG-IsErr b))
    nil
    (progn
      (setq r (vl-catch-all-apply '(lambda () (vla-get-IsDynamicBlock b))))
      (KG-ComBool r)
    )
  )
)

(defun KG_EXDeleteDef (name / b r)
  (setq b (KG-BlockObj name))
  (if (or (not b) (KG-IsErr b))
    nil
    (progn
      (setq r (vl-catch-all-apply '(lambda () (vla-Delete b))))
      (not (KG-IsErr r))
    )
  )
)

;; Сколько вхождений в чертеже ссылаются на каждое определение.
;;
;; Один проход по всем определениям, включая содержимое других
;; определений. По имени понять, свободно ли определение, нельзя: PURGE
;; отказывается удалять «~X», пока на него ссылается хотя бы одно
;; вхождение -- в том числе внутри другого неиспользуемого определения.
;; Карта ссылок на определения: имя -> список определений, внутри
;; которых есть его вставка (с повторами, длина списка = число ссылок).
;;
;; Только DXF: tblnext -> tblobjname -> entnext -> entget. Ни одного
;; COM-вызова. Обход определений через vlax-for с чтением
;; EffectiveName/Name у вложенной вставки на реальном чертеже дал
;; 0xC0000005 -- нарушение доступа, которое vl-catch-all-apply не
;; ловит. В чертеже, где сиротские *U47/51/52/53/55/56 были удалены
;; PURGE, тот же код работал; с ними -- падал.
;;
;; Имя берётся из группы 2, то есть ФАКТИЧЕСКОЕ. У анонимной вставки
;; динамического блока там *U77, а не имя родителя: значит, родитель
;; получит ноль ссылок. Это осознанно -- удаление родителя AutoCAD всё
;; равно отклонит, пока живо его анонимное представление, а
;; многопроходный цикл сначала убирает сиротские *U.
;; 71.3. Якорные вложения: PURGE снимает определение, только когда на него
;; никто не ссылается, а мастер-версия и вариант с нулём вставок выглядят
;; именно «мёртвыми». На время очистки на защищённые имена ставятся
;; технические вложения в начало координат; снимаются в конце очистки
;; (KG-PurgeAnchorsDrop), в том числе обработчиком ошибок.
(defun KG-PurgeAnchorsEnsure ( / nm protect e before)
  (if (null KG-PURGE-ANCHORS)
    (progn
      (setq protect
        (KG-CleanupKeepAll (KG-Safe '(lambda () (KG_EXAllDefNames)) nil)))
      (foreach nm protect
        (setq before (entlast))
        (if (KG-Safe '(lambda () (entmake (list '(0 . "INSERT")
                                                (cons 2 nm)
                                                '(10 0.0 0.0 0.0))))
                     nil)
          (progn
            (setq e (entlast))
            (if (not (eq e before))
              (setq KG-PURGE-ANCHORS (cons (cons nm e) KG-PURGE-ANCHORS))
            )
          )
        )
      )
      (if (and KG-TRACE-DETAIL KG-PURGE-ANCHORS)
        (princ (strcat "\nЗащита от PURGE: якорных вложений "
                       (itoa (length KG-PURGE-ANCHORS))))
      )
      ;; 71.9: якоря -- часть состояния, которое обязано пережить падение.
      (KG-JournalWrite)
    )
  )
)

;; Снять якорные вложения. Если якорь создал анонимное представление
;; динамического блока (*U), оно снимается сразу же: после снятия якоря оно
;; осталось бы сиротой и копилось бы новым мусором.
(defun KG-PurgeAnchorsDrop ( / p e g2)
  (foreach p KG-PURGE-ANCHORS
    (setq e (cdr p))
    (setq g2 (KG-Safe '(lambda () (cdr (assoc 2 (entget e)))) nil))
    (KG-Safe '(lambda () (entdel e)) nil)
    (if (and g2 (= (type g2) (type "")) (KG-IsAnonDynName g2))
      (KG-Safe '(lambda () (KG_EXEraseAnonDef g2)) nil)
    )
  )
  (setq KG-PURGE-ANCHORS nil)
)

;; 72.7. Сколько в таблице блоков определений каждого вида. Нужно для
;; одной сводной строки после PURGE: сам PURGE печатает по строке на
;; каждый удалённый блок, и журнал обрезается. Считаем только имена,
;; чтобы не читать содержимое определений.
(defun KG-CountBlockKinds ( / u td nm names)
  (setq u 0 td 0)
  (setq names (KG-Safe '(lambda () (KG_EXAllDefNames)) nil))
  (foreach nm names
    (if (KG-IsAnonDynName nm) (setq u (1+ u)))
    (if (KG-IsTempDefName nm) (setq td (1+ td)))
  )
  (list u td)
)

;; Два прохода AutoCAD PURGE по блокам. Два, а не один: сиротские *U
;; держат на себе старые вложенные определения, первый проход снимает
;; *U, второй -- освободившееся. Ровно то, что вручную делает двойной
;; PURGE, и PURGE в отличие от нас живое представление не тронет.
(defun KG-CleanupPurgeBlocks ( / n ce mt kg-t0 k0 k1 u0 t0 u1 t1)
  ;; Ключевые слова с подчёркиванием (_B, _N): без него AutoCAD ждёт
  ;; букву своей локализации, а у пользователя AutoCAD русский.
  ;; Пустого ввода в конце быть не должно: после _N PURGE завершается
  ;; сам, а лишний Enter уходит в командную строку и повторяет
  ;; последнюю команду -- отсюда «Неизвестная команда INTCLEANUP».
  ;; 71.3: пока определение «использовано» -- а якорное вложение именно это
  ;; и делает -- PURGE его не снимает. Иначе мастер-версия и варианты с
  ;; нулём вставок вычищались бы подчистую.
  ;; 71.6. Суб-замеры: якоря и каждый проход PURGE меряются отдельно.
  ;; Строка «очистка: PURGE блоков» не говорила, якорные это вложения
  ;; или сам PURGE.
  (setq kg-t0 (KG-SubT0))
  (KG-PurgeAnchorsEnsure)
  (KG-SubT1 "пурге: якорные вложения" kg-t0)
  (setq ce (getvar "CMDECHO"))
  ;; NOMUTT и CMDECHO НЕ подавляют в AutoCAD 2023 вывод самого -PURGE
  ;; («Удаление блок ...»): это проверено на живом чертеже и на
  ;; accoreconsole. Настройки оставлены, чтобы не было эха команд, а
  ;; сводка ниже даёт одну понятную строку вместо сотен.
  (setq mt (getvar "NOMUTT"))
  (setvar "CMDECHO" 0)
  (setvar "NOMUTT" 1)
  (setq k0 (KG-CountBlockKinds) u0 (car k0) t0 (car (cdr k0)))
  (setq n 0)
  (while (< n 3)
    (setq n (1+ n))
    (setq kg-t0 (KG-SubT0))
    (KG-Safe '(lambda () (command "_.-PURGE" "_B" "*" "_N")) nil)
    (KG-SubT1 (strcat "пурге: проход " (itoa n)) kg-t0)
  )
  (setvar "NOMUTT" mt)
  (setvar "CMDECHO" ce)
  (setq k1 (KG-CountBlockKinds) u1 (car k1) t1 (car (cdr k1)))
  (if (or (> u0 u1) (> t0 t1))
    (princ (strcat "\nОчистка: снято блоков «*U...»: "
                   (itoa (max 0 (- u0 u1)))
                   ", временных «~...»: "
                   (itoa (max 0 (- t0 t1)))))
  )
  t
)

;; Техническая вставка из буфера в начало координат.
;; Пробуем PASTECLIP, затем PASTEBLOCK. Возвращает T/nil.
(defun KG_EXPasteAtOrigin ( / ok)
  (setq ok nil)
  (foreach cmd '("_.PASTECLIP" "_.PASTEBLOCK")
    (if (not ok)
      (progn
        (setq ok (vl-catch-all-apply
                   '(lambda ()
                      (setvar "CMDECHO" 0)
                      (command cmd (list 0.0 0.0 0.0))
                      (while (> (getvar "CMDACTIVE") 0) (command))
                      t)))
        (if (KG-IsErr ok) (setq ok nil))
      )
    )
  )
  ok
)

;; Снимок handle'ов всех вхождений
(defun KG-SnapshotDrawing ( / ss i out)
  (setq out nil)
  (setq ss (ssget "_X" '((0 . "INSERT"))))
  (if ss
    (repeat (setq i (sslength ss))
      (setq out (cons (cdr (assoc 5 (entget (ssname ss (setq i (1- i)))))) out))
    )
  )
  (reverse out)
)

;; Новые вхождения, появившиеся после снимка
(defun KG_EXNewInstancesSince (snapshot / ss i h out)
  (setq out nil)
  (setq ss (ssget "_X" '((0 . "INSERT"))))
  (if ss
    (repeat (setq i (sslength ss))
      (setq h (cdr (assoc 5 (entget (ssname ss (setq i (1- i)))))))
      (if (not (member h snapshot)) (setq out (cons h out)))
    )
  )
  (reverse out)
)

;; Модель экземпляра по handle
(defun KG_EXInstanceHandle (handle / e obj r)
  ;; Чтение свойств одного вхождения может не удаться (анонимный
  ;; динамический блок, объект внешней ссылки). Ошибка здесь не должна
  ;; обрывать команду -- раньше именно на этом месте падал INTEGRATE.
  (setq r
    (vl-catch-all-apply
      '(lambda ()
         (setq e (handent (KG-AsString handle)))
         (if e
           (progn
             (setq obj (vlax-ename->vla-object e))
             (KG-InstanceModel obj e)
           )
           nil))))
  (if (KG-IsErr r)
    (progn
      (princ (strcat "\nВНИМАНИЕ: вхождение " (KG-AsString handle)
                     " не удалось прочитать, оно пропущено."))
      nil)
    r
  )
)

;; Создать экземпляр в том же пространстве с теми же свойствами.
;; Возвращает handle нового экземпляра или nil.
(defun KG_EXCreateInstance (defname instmodel / space blk owner newobj atts pt)
  (setq blk (KG-BlockObj defname))
  (if (or (not blk) (KG-IsErr blk))
    nil
    (progn
      ;; целевое пространство: то же, что у исходного экземпляра
      (setq owner
        (cond
          ((KG-StrEq (KG-CdrCI "space" instmodel) "Model") (KG-Model))
          (t (KG-LayoutBlockForSpace (KG-CdrCI "space" instmodel)))
        )
      )
      ;; Лист по имени не найден: МОДЕЛЬ НЕ подставляется. Тихий откат
      ;; в модель уводил экземпляр с листа в чужое пространство (живой
      ;; прогон, 17.10); теперь это отказ -- вызывающий оставляет
      ;; старый экземпляр на месте и сообщает о нём.
      (if (null owner)
        nil
        (progn
          ;; все числовые аргументы приводятся: (if значение …) не спасает,
          ;; когда значение есть, но не число, а nil дал бы «fixnump: nil»
          (setq pt (KG-CdrCI "pos" instmodel))
          (if (or (null pt) (< (length pt) 3)) (setq pt (list 0.0 0.0 0.0)))
          (setq newobj
            (vl-catch-all-apply
              '(lambda ()
                 (vla-InsertBlock owner
                   (vlax-3d-point (list (KG-AsNum (nth 0 pt) 0.0)
                                        (KG-AsNum (nth 1 pt) 0.0)
                                        (KG-AsNum (nth 2 pt) 0.0)))
                   defname
                   (KG-AsNum (KG-CdrCI "sx" instmodel) 1.0)
                   (KG-AsNum (KG-CdrCI "sy" instmodel) 1.0)
                   (KG-AsNum (KG-CdrCI "sz" instmodel) 1.0)
                   (KG-AsNum (KG-CdrCI "rot" instmodel) 0.0))))
          )
          (if (KG-IsErr newobj)
            nil
            (progn
              (vl-catch-all-apply
                '(lambda () (vla-put-Layer newobj (KG-CdrCI "layer" instmodel))))
              (if (vlax-property-available-p newobj 'Annotative)
                (vl-catch-all-apply
                  '(lambda ()
                     (vla-put-Annotative newobj
                       (if (KG-CdrCI "annotative" instmodel) :vlax-true :vlax-false))))
              )
              (KG-SetAttributeValues newobj (KG-CdrCI "attrs" instmodel))
              (cdr (assoc 5 (entget (vlax-vla-object->ename newobj))))
            )
          )
        )
      )
    )
  )
)

;; Блок-владелец для имени пространства (имени листа)
(defun KG-LayoutBlockForSpace (spacename / lays lay res blk)
  (setq res nil)
  (setq lays (vl-catch-all-apply '(lambda () (vla-get-Layouts (KG-Doc)))))
  (if (not (KG-IsErr lays))
    (vlax-for lay lays
      (if (and (null res) (KG-StrEq (vla-get-Name lay) spacename))
        (setq blk (vl-catch-all-apply '(lambda () (vla-get-Block lay))))
      )
    )
  )
  (if (KG-IsErr blk) nil blk)
)

;; Смена эффективного имени вхождения (перепривязка на другое определение)
(defun KG_EXSetEffectiveName (handle defname / e obj r sp)
  (setq e (handent (KG-AsString handle)))
  (if (null e)
    nil
    (progn
      (setq obj (vlax-ename->vla-object e))
      (setq sp (KG-Safe '(lambda () (KG-SpaceOf e)) nil))
      (if (and sp (/= (KG-AsString sp) "") (not (KG-StrEq (KG-AsString sp) "nil")))
        ;; На чертеже: пересоздаём экземпляр для сохранения динамических свойств и *U
        (if (KG-RecreateInstanceSamePlace e defname) t nil)
        ;; Внутри определения блока: перепривязываем имя
        (progn
          (setq r (vl-catch-all-apply '(lambda () (vla-put-Name obj defname))))
          (if (KG-IsErr r)
            (if (KG-RecreateInstanceSamePlace e defname) t nil)
            t
          )
        )
      )
    )
  )
)

;; Пересоздать вхождение на месте с другим определением
(defun KG-RecreateInstanceSamePlace (e defname / obj m h dyn nv att oldh)
  (setq obj (vlax-ename->vla-object e))
  (setq m (KG-InstanceModel obj e))
  (setq oldh (cdr (assoc 5 (entget e))))
  (setq h (KG_EXCreateInstance defname m))
  (if h
    (progn
      (setq dyn (KG-CdrCI "dyn-props" m))
      (if dyn (KG_EXRestoreDynProps h dyn))
      (setq nv (KG-CdrCI "nested-vis" m))
      (if nv
        (foreach pair nv
          (KG_EXSetNestedVisibility h (car pair) (cdr pair))
        )
      )
      (setq att (KG-CdrCI "attrs" m))
      (if (and att (handent (KG-AsString h)))
        (KG-Safe '(lambda () (KG-SetAttributeValues (vlax-ename->vla-object (handent (KG-AsString h))) att)) nil)
      )
      (if oldh (KG_EXDeleteInstance oldh))
    )
  )
  h
)

(defun KG_EXDeleteInstance (handle / e r)
  (setq e (handent (KG-AsString handle)))
  (if (null e)
    nil
    (progn
      (setq r (vl-catch-all-apply
                '(lambda () (vla-Delete (vlax-ename->vla-object e)))))
      (not (KG-IsErr r))
    )
  )
)

;; Восстановить динамические свойства верхнего блока.
;; 72.1. Карта «имя свойства -> объект свойства» собирается ОДНИМ проходом по
;; списку свойств (P COM-вызовов). Прежний код на КАЖДОЕ сохранённое свойство
;; заново перебирал весь список и спрашивал имя по COM: D*P вызовов -- в живом
;; прогоне это дало 72.7 с на 100 экземпляров, главный остаток шага «замена
;; экземпляров». Поиск в карте -- KG-RMCdr (точный assoc, без учёта регистра
;; запасным путём). Совпадающие значения не переписываются вовсе (KG-DynValEq):
;; запись динамического свойства запускает пересборку анонимного представления,
;; и пропуск ничего не меняющих записей экономит больше, чем один COM-вызов.
;; 72.2. Суб-замеры внутри переноса: где именно уходит время.
;; «вход (работа)» -- handent, vla-object и получение списка свойств;
;; «карта имён» -- построение карты «имя -> свойство» одним проходом;
;; «значения (работа)» -- весь проход по сохранённым свойствам;
;; «чтение (работа)» -- чтение текущего значения перед сверкой;
;; «запись (работа)» -- цепочка попыток записи одного свойства.
;; Счётчики (это число вызовов, не время): «совпало», «записано»,
;; «не удалось», «попытки записи» и «без пары» (сохранённому имени
;; свойства среди текущих не нашлось).
(defun KG_EXRestoreDynProps (handle dynprops / e obj props p nm val n pnm r vval
                                            pmap cur curv kg-t0 kg-tr kg-tw)
  (setq n 0)
  (setq e (handent (KG-AsString handle)))
  (if (and e dynprops)
    (progn
      (setq kg-t0 (KG-SubT0))
      (setq obj (vlax-ename->vla-object e))
      (setq props (vl-catch-all-apply
                    '(lambda () (vlax-invoke obj 'GetDynamicBlockProperties))))
      (KG-SubT1 "замена: свойства -- вход (работа)" kg-t0)
      (if (and (not (KG-IsErr props)) props)
        (progn
          (setq kg-t0 (KG-SubT0))
          (setq pmap nil)
          (foreach p props
            (setq pnm (vl-catch-all-apply '(lambda () (vla-get-PropertyName p))))
            (if (and (not (KG-IsErr pnm)) (= (type pnm) 'STR) (/= pnm ""))
              (setq pmap (KG-RMSet pnm p pmap))
            )
          )
          (KG-SubT1 "замена: свойства -- карта имён" kg-t0)
          (setq kg-t0 (KG-SubT0))
          (foreach dp dynprops
            (setq nm (car dp))
            (setq val (cdr dp))
            (setq vval (vl-catch-all-apply '(lambda () (vlax-variant-value val))))
            (if (or (KG-IsErr vval) (null vval)) (setq vval val))
            (setq p (KG-RMCdr nm pmap))
            (if p
              (progn
                ;; Текущее значение: нужно и для сверки равенства. Не прочиталось --
                ;; curv = nil, и тогда пишем, как раньше (безопасный путь).
                (setq kg-tr (KG-SubT0))
                (setq cur (vl-catch-all-apply '(lambda () (vlax-get-property p 'Value))))
                (if (KG-IsErr cur)
                  (setq curv nil)
                  (progn
                    (setq curv (vl-catch-all-apply
                                 '(lambda () (vlax-variant-value cur))))
                    (if (or (KG-IsErr curv) (null curv)) (setq curv cur))
                  )
                )
                (KG-SubT1 "замена: свойства -- чтение (работа)" kg-tr)
                (if (KG-DynValEq curv vval)
                  ;; Совпало -- не пишем вовсе: запись пересобирает анонимное
                  ;; представление блока, это самая дорогая операция.
                  (progn
                    (setq n (1+ n))
                    (KG-SubAdd "замена: свойства -- совпало" 0)
                  )
                  (progn
                    (setq kg-tw (KG-SubT0))
                    ;; 1. исходный variant (как раньше)
                    (KG-SubAdd "замена: свойства -- попытки записи" 0)
                    (setq r (vl-catch-all-apply
                              '(lambda () (vlax-put-property p 'Value val))))
                    ;; 2. строковый variant (для параметров с выбором)
                    (if (and (KG-IsErr r) (or (= (type vval) 'STR) (null (type vval))))
                      (progn
                        (KG-SubAdd "замена: свойства -- попытки записи" 0)
                        (setq r (vl-catch-all-apply
                                  '(lambda () (vlax-put-property p 'Value (vlax-make-variant (KG-AsString vval) vlax-vbString)))))
                      )
                    )
                    ;; 3. вещественный variant (для углов и длин)
                    (if (and (KG-IsErr r) (= (type vval) 'REAL))
                      (progn
                        (KG-SubAdd "замена: свойства -- попытки записи" 0)
                        (setq r (vl-catch-all-apply
                                  '(lambda () (vlax-put-property p 'Value (vlax-make-variant vval vlax-vbDouble)))))
                      )
                    )
                    ;; 4. целочисленный variant
                    (if (and (KG-IsErr r) (= (type vval) 'INT))
                      (progn
                        (KG-SubAdd "замена: свойства -- попытки записи" 0)
                        (setq r (vl-catch-all-apply
                                  '(lambda () (vlax-put-property p 'Value (vlax-make-variant vval vlax-vbLong)))))
                      )
                    )
                    ;; 5. универсальный vlax-put
                    (if (KG-IsErr r)
                      (progn
                        (KG-SubAdd "замена: свойства -- попытки записи" 0)
                        (setq r (vl-catch-all-apply
                                  '(lambda () (vlax-put p 'Value vval))))
                      )
                    )
                    ;; 6. последняя повторная попытка
                    (if (KG-IsErr r)
                      (progn
                        (KG-SubAdd "замена: свойства -- попытки записи" 0)
                        (setq r (vl-catch-all-apply
                                  '(lambda () (vlax-put-property p 'Value vval))))
                      )
                    )
                    (KG-SubT1 "замена: свойства -- запись (работа)" kg-tw)
                    (if (not (KG-IsErr r))
                      (progn
                        (setq n (1+ n))
                        (KG-SubAdd "замена: свойства -- записано" 0)
                      )
                      (progn
                        (KG-SubAdd "замена: свойства -- не удалось" 0)
                        (if (< (length KG-DYN-FAIL) 30)
                          (setq KG-DYN-FAIL
                            (cons (list (KG-AsString handle) (KG-AsString nm)
                                        (KG-AsString vval) "запись")
                                  KG-DYN-FAIL))))
                    )
                  )
                )
              )
              (progn
                (KG-SubAdd "замена: свойства -- без пары" 0)
                (if (< (length KG-DYN-FAIL) 30)
                  (setq KG-DYN-FAIL
                    (cons (list (KG-AsString handle) (KG-AsString nm)
                                (KG-AsString vval) "нет пары")
                          KG-DYN-FAIL))))
            )
          )
          (KG-SubT1 "замена: свойства -- значения (работа)" kg-t0)
        )
      )
    )
  )
  n
)

(defun KG_EXSetNestedVisibility (handle nestedname value / e def sub out r)
  (setq out nil)
  (setq e (KG-Call 'handent (list handle) nil))
  (if e
    (progn
      ;; После записи динамических свойств верхнего блока вставка
      ;; указывает не на определение варианта, а на анонимное
      ;; представление *U: вложенные вставки этого экземпляра лежат там.
      (setq def (KG_DefNameOfEnt e))
      (cond
        ((and (KG-IsAnonDynName def)
              (setq sub (KG-Call 'KG-DefInsertByName (list def nestedname) nil)))
         (setq r (KG-Call 'KG-SetVisibilityState (list sub value) nil))
         (setq out (if r t nil))
        )
        ((KG-IsAnonDynName def)
         ;; представление есть, а нужной вложенной вставки в нём нет
         (setq out "НЕ НАЙДЕН")
        )
        (t
         ;; представления нет: вставка смотрит прямо на определение
         ;; варианта. Писать туда нельзя -- определение общее для всех
         ;; экземпляров, а состояние нужно только этому.
         (setq out "НЕТ ПРЕДСТАВЛЕНИЯ")
        )
      )
    )
  )
  out
)

;; Геометрия и вложенные динамические блоки переносятся полностью.
;;; Копирование определения блока С СОХРАНЕНИЕМ ДИНАМИЧЕСКИХ СВОЙСТВ.
;;;
;;; Обычное «создать пустое определение и скопировать в него объекты»
;;; даёт СТАТИЧЕСКИЙ блок: параметры динамического блока лежат в словаре
;;; расширения BLOCK_RECORD (ACAD_ENHANCEDBLOCK), API их не отдаёт, и при
;;; таком копировании они не переносятся. Обход: определение клонируется
;;; в невидимый документ ObjectDBX (в памяти), там переименовывается и
;;; копируется обратно -- так динамические свойства сохраняются.
;;; Приём Lee Mac (LM:CopyBlockDefinition).
;; Каждый шаг пишется в KG-DBX-ERR: на реальном чертеже «ObjectDBX
;; недоступен» означал на самом деле «интерфейс получен, а отказал один из
;; шести шагов копирования», и какой именно -- видно не было.
(defun KG_EXCopyDefDeep (srcname newname / dbx abc dbc def out tmp)
  (setq out nil)
  (if (KG_EXDefExists newname)
    t
    (progn
      (setq KG-DBX-ERR nil)
      (setq dbx (KG-ObjectDbx))
      (if (not dbx)
        (if (not KG-DBX-ERR)
          (KG-DBX-Fail "интерфейс ObjectDBX не получен, причина не сообщена")
        )
        (progn
          (setq abc (KG-Safe '(lambda () (KG-Blocks)) nil))
          (if (not abc)
            (KG-DBX-Fail "таблица блоков чертежа не получена")
          )
          (setq dbc (KG-DBX-Try "таблица блоков ObjectDBX (vla-get-Blocks)"
                                '(lambda () (vla-get-Blocks dbx))))
          (setq def (KG-BlockObj srcname))
          (if (or (not def) (KG-IsErr def))
            (KG-DBX-Fail (strcat "определение-источник \"" srcname
                                 "\" не найдено в чертеже"))
          )
          (if (and abc dbc def (not (KG-IsErr def)))
            (progn
              ;; КОРЕНЬ ПРОБЛЕМЫ СО СТАТИЧЕСКИМ ВАРИАНТОМ.
              ;; Document.CopyObjects и Database.CopyObjects -- методы БЕЗ
              ;; возвращаемого значения, vlax-invoke от них даёт nil. Код
              ;; проверял результат вызова и поэтому никогда не шёл дальше
              ;; первого копирования: ни ошибки, ни результата.
              ;; Проверяется не возвращаемое значение, а ПОСЛЕДСТВИЕ --
              ;; появилось ли определение в целевой таблице блоков.
              (KG-DBX-Try "копирование в документ ObjectDBX (CopyObjects)"
                '(lambda ()
                   (vlax-invoke (KG-Doc) 'CopyObjects (list def) dbc)))
              (setq tmp (KG-Safe '(lambda () (vla-Item dbc srcname)) nil))
              (if (or (not tmp) (KG-IsErr tmp))
                (KG-DBX-Fail
                  (strcat "после CopyObjects в документе ObjectDBX нет \""
                          srcname "\""))
                (progn
                  (KG-DBX-Try
                    (strcat "переименование \"" srcname "\" -> \""
                            newname "\" внутри ObjectDBX")
                    '(lambda () (vla-put-Name tmp newname)))
                  (setq def (KG-Safe '(lambda () (vla-Item dbc newname)) nil))
                  (if (or (not def) (KG-IsErr def))
                    (KG-DBX-Fail
                      (strcat "после переименования в ObjectDBX нет \""
                              newname "\""))
                    (progn
                      (KG-DBX-Try
                        "копирование из ObjectDBX в чертёж (CopyObjects)"
                        '(lambda ()
                           (vlax-invoke dbx 'CopyObjects (list def) abc)))
                      (setq out (KG-Safe '(lambda () (KG_EXDefExists newname))
                                         nil))
                      (if (not out)
                        (KG-DBX-Fail
                          (strcat "после копирования определения \""
                                  newname "\" в чертеже нет"))
                      )
                    )
                  )
                )
              )
            )
          )
          (KG-Safe '(lambda () (vlax-release-object dbx)) nil)
        )
      )
      out
    )
  )
)

;;; Запасной путь: скопировать только объекты определения. Работает без
;;; ObjectDBX, но результат СТАТИЧЕСКИЙ -- динамика мастера теряется.
(defun KG-EXCreateDefStatic (newname mastername / src dst arr i n objs r)
  (setq src (KG-BlockObj mastername))
  (if (or (not src) (KG-IsErr src))
    nil
    (if (KG_EXDefExists newname)
      t
      (progn
        (setq dst (vl-catch-all-apply
                    '(lambda () (vla-Add (KG-Blocks)
                                  (vlax-3d-point '(0.0 0.0 0.0)) newname))))
        (if (KG-IsErr dst)
          nil
          (progn
            (setq objs nil n 0)
            (vlax-for e src (setq n (1+ n)))
            (if (= n 0)
              t
              (progn
                (setq arr (vlax-make-safearray vlax-vbobject (cons 0 (1- n))))
                (setq i 0)
                (vlax-for e src
                  (vlax-safearray-put-element arr i e)
                  (setq i (1+ i))
                )
                (setq r (vl-catch-all-apply
                          '(lambda () (vla-CopyObjects (KG-Doc) arr dst nil))))
                (not (KG-IsErr r))
              )
            )
          )
        )
      )
    )
  )
)

;;;--- RDBDBXTEST (INTDBXTEST): сохраняется ли динамика при копировании определения ----
;;;
;;; Проба для реального AutoCAD: создаёт копию выбранного определения через
;;; ObjectDBX под именем «имя~тест», печатает, осталась ли копия
;;; динамической, и удаляет её. Чертеж не меняется.
(defun C:RDBDBXTEST ( / sel e nm test b ok dyn)
  (vl-load-com)
  (princ "\n=== RDBDBXTEST: проверка глубокого клонирования ===")
  (KG-SayKV "ACADVER" (KG-AsString (getvar "ACADVER")))
  (if (not (KG-Safe '(lambda () (KG-ObjectDbx)) nil))
    (progn
      (princ "\nОШИБКА: интерфейс ObjectDBX получить не удалось.")
      (princ "\nВарианты будут создаваться статическими.")
      (if KG-DBX-ERR
        (progn
          (princ "\nЧто пробовалось:")
          (foreach m (reverse KG-DBX-ERR) (princ (strcat "\n  " m)))
        )
      )
    )
    (progn
      (princ "\nObjectDBX доступен.")
      (setq sel (KG-Safe '(lambda () (entsel "\nВыберите блок для пробы: ")) nil))
      (if (or (null sel) (KG-IsErr sel))
        (princ "\nНичего не выбрано.")
        (progn
          (setq e (car sel))
          (setq nm (KG-EffectiveNameOf (vlax-ename->vla-object e)))
          (setq test (strcat nm "~тест"))
          (if (KG_EXDefExists test) (KG_EXDeleteDef test))
          (setq ok
            (KG-DBX-Try (strcat "глубокое копирование \"" nm "\" -> \""
                                test "\"")
                        '(lambda () (KG_EXCopyDefDeep nm test))))
          (if (not ok)
            (progn
              (princ "\nОШИБКА: скопировать определение не удалось.")
              (if KG-DBX-ERR
                (progn
                  (princ "\nОтказавшие шаги:")
                  (foreach m (reverse KG-DBX-ERR)
                    (princ (strcat "\n  " m)))
                )
              )
            )
            (progn
              (setq b (KG-BlockObj test))
              (setq dyn (KG-ComBool
                          (KG-Safe '(lambda () (vla-get-IsDynamicBlock b)) nil)))
              (princ (strcat "\nКопия \"" test "\" создана."))
              (princ (strcat "\nКопия динамическая: " (if dyn "ДА" "НЕТ")))
              (KG_EXDeleteDef test)
              (princ "\nПробное определение удалено, чертеж не изменён.")
            )
          )
        )
      )
    )
  )
  (princ)
)
(defun C:INTDBXTEST () (C:RDBDBXTEST))
(defun C:ПДБТЕСТDBX () (C:RDBDBXTEST))

;;;--- RDBRENAMETEST (INTRENAMETEST) ----------------------------------------
;;; Проба: сохраняет ли vla-put-Name динамические свойства определения.
;;;
;;; От ответа зависит запасной путь построения варианта БЕЗ ObjectDBX:
;;; освободить имя мастера, вставить из буфера ещё раз (придёт новое
;;; динамическое определение) и переименовать его в имя варианта. Если
;;; переименование динамику ломает -- этот путь неприменим.
;;;
;;; Проба обратима: имя возвращается на место.
(defun C:RDBRENAMETEST ( / sel e nm b d0 tmp r d1 d2)
  (vl-load-com)
  (princ "\n=== RDBRENAMETEST: переименование и динамика ===")
  (setq sel (KG-Safe '(lambda () (entsel "\nВыберите блок для пробы: ")) nil))
  (if (or (null sel) (KG-IsErr sel))
    (princ "\nНичего не выбрано.")
    (progn
      (setq e (car sel))
      (setq nm (KG-EffectiveNameOf (vlax-ename->vla-object e)))
      (setq b (KG-BlockObj nm))
      (setq d0 (KG-Safe '(lambda () (KG-EXDefIsDynamic nm)) nil))
      (KG-SayKV "Определение" (KG-AsString nm))
      (KG-SayKV "Динамическое до пробы" (if d0 "ДА" "НЕТ"))
      (if (not d0)
        (princ "\nОпределение статическое -- пробовать нечего, возьмите динамическое.")
        (progn
          (setq tmp (strcat nm "~проба"))
          (if (KG-Safe '(lambda () (KG_EXDefExists tmp)) nil)
            (princ (strcat "\nИмя \"" tmp "\" уже занято -- проба отменена."))
            (progn
              (setq r (KG-Safe '(lambda () (vla-put-Name b tmp)) nil))
              (if (KG-IsErr r)
                (princ (strcat "\nПереименовать не удалось: "
                               (KG-AsString (vl-catch-all-error-message r))))
                (progn
                  (setq d1 (KG-Safe '(lambda () (KG-EXDefIsDynamic tmp)) nil))
                  (KG-SayKV "Динамическое после переименования"
                            (if d1 "ДА" "НЕТ"))
                  (KG-Safe '(lambda () (vla-put-Name (KG-BlockObj tmp) nm)) nil)
                  (setq d2 (KG-Safe '(lambda () (KG-EXDefIsDynamic nm)) nil))
                  (KG-SayKV "Имя возвращено на место"
                            (if (KG-Safe '(lambda () (KG_EXDefExists nm)) nil)
                              "ДА" "НЕТ"))
                  (KG-SayKV "Динамическое после возврата" (if d2 "ДА" "НЕТ"))
                  (princ
                    (if (and d1 d2)
                      (strcat "\nВЫВОД: переименование динамику СОХРАНЯЕТ -- "
                              "вариант можно строить повторной вставкой из "
                              "буфера и переименованием, без ObjectDBX.")
                      (strcat "\nВЫВОД: переименование динамику ЛОМАЕТ -- "
                              "запасной путь неприменим, нужен ObjectDBX.")))
                )
              )
            )
          )
        )
      )
    )
  )
  (princ)
)
(defun C:INTRENAMETEST () (C:RDBRENAMETEST))
(defun C:ПДБТЕСТПЕРЕИМ () (C:RDBRENAMETEST))

;;;--- RDBCLEANUP (INTCLEANUP, ПДБОЧИСТКА) ----------------------------------
;;; Удалить определения, оставшиеся от интеграции.
;;;
;;; PURGE здесь не помогает из-за ПОРЯДКА: старый вариант семейства
;;; («Комплект КП50 v1.1») сам больше никем не используется, но СОДЕРЖИТ
;;; вхождения служебных определений. Пока он не удалён, каждое служебное
;;; считается использованным и не очищается. Команда удаляет в несколько
;;; проходов: за один проход освобождается то, на что ссылок не осталось.
;;;
;;; Новейшая итерация каждого семейства не удаляется даже при нуле
;;; ссылок -- это источник, из которого строятся варианты.
(defun KG-CleanupRun ( / holders counts names keep cand nm deleted progress
                        round ans hh orph left udel ufail uor uwhy inside round2
                        noxref goon uor2 rpairs rn n1 n uerr kg-t0 kg-del)
  (vl-load-com)
  (princ "\n=== INTCLEANUP: очистка определений прошлой интеграции ===")

  ;; Пересчёт нужен и до вопроса, и в каждом проходе, и после: карта
  ;; ссылок меняется по мере удаления.
  (KG-MarkT "очистка: карта ссылок")
  (setq holders (KG-Safe '(lambda () (KG-EXRefHolders)) nil))
  (if (null holders)
    ;; Без карты ссылок продолжать нельзя: всё оказалось бы «без
    ;; ссылок», и очистка сняла бы живые определения.
    (princ (strcat "\nОШИБКА: карту ссылок построить не удалось "
                   "(вставок не найдено или выборка не сработала). "
                   "Очистка остановлена, чертёж не изменён."))
    (progn
      ;; маркер успешной выборки лежит в car, карта -- в cdr
      (setq holders (cdr holders))
  (setq counts (KG-CleanupCounts holders))
  (KG-MarkT "очистка: список определений")
  (setq names (KG-Safe '(lambda () (KG_EXAllDefNames)) nil))
  (setq keep (KG-CleanupKeepAll names))
  (KG-MarkT "очистка: подбор кандидатов")
  (setq cand (KG-CleanupCandidates counts names keep))
  (setq orph (KG-CleanupOrphans counts names))
  (KG-MarkT "очистка: кандидаты подобраны")

  (if (and (not cand) (not orph))
    (princ "\nЧисто: ни свободных определений, ни сиротских *U.")
    (progn
      (if cand
        (princ (strcat "\nСвоих определений без ссылок: "
                       (itoa (length cand))))
      )
      (if orph
        (princ (strcat "\nСиротских анонимных представлений (*U): "
                       (itoa (length orph))))
      )
      ;; Списки имён целиком -- только при KG-TRACE-DETAIL: на большом
      ;; чертеже это сотни строк, и хвост журнала терялся. Числа
      ;; печатаются всегда, а имена остатка -- в конце, с держателями.
      (if (and KG-TRACE-DETAIL cand) (KG-PrincList cand 10))
      (if (and KG-TRACE-DETAIL orph) (KG-PrincList orph 10))
      (setq ans "Да")
      (if KG-CLEANUP-ASK
        (progn
          (initget "Да Нет Yes No")
          (setq ans (getkword "\nОчистить? [Да/Нет] <Да>: "))
          (if (null ans) (setq ans "Да"))
        )
      )
      (if (or (KG-StrEq ans "Да") (KG-StrEq ans "Yes"))
        (progn
          ;; Сначала -- возврат ссылок с прошлых имён. Без этого шага
          ;; «~ИМЯ» держатся вложениями внутри чужих определений и
          ;; анонимных представлений: они «использованы», и ни PURGE, ни
          ;; стирание их не берут. Возврат делает это молча и адресно --
          ;; именно этого не хватало, чтобы очистка доходила до конца.
          (setq kg-t0 (KG-SubT0))
          (setq rpairs (KG-Call 'KG-CleanupRestorePairs (list names) nil))
          (KG-SubT1 "очистка: подбор возвратов (работа)" kg-t0)
          (if rpairs
            (progn
              (KG-MarkT "очистка: возврат ссылок с прошлых имён")
              (setq kg-t0 (KG-SubT0))
              (setq rn (KG-AsNum (KG-Call 'KG-Step_RewireDefs (list rpairs) 0) 0))
              (KG-SubT1 "очистка: возврат ссылок (работа)" kg-t0)
              (princ (strcat "\nВозвращено ссылок с прошлых имён: "
                             (itoa rn)))
            )
          )
          (setq deleted nil udel nil ufail nil uwhy nil uerr nil)
          (setq round 0)
          (if KG-CLEANUP-DELETE
            (progn
              (setq progress t)
              (while (and progress (< round 8))
                (setq round (1+ round))
                (KG-MarkT (strcat "очистка: проход " (itoa round)))
                (setq holders
                  (KG-Unmark (KG-Safe '(lambda () (KG-EXRefHolders)) nil)))
                (setq counts (KG-CleanupCounts holders))
                (setq names (KG-Safe '(lambda () (KG_EXAllDefNames)) nil))
                (setq keep (KG-CleanupKeepAll names))
                (setq cand (KG-CleanupCandidates counts names keep))
                (setq progress nil)
                (foreach nm cand
                  (KG-MarkT (strcat "удаление определения \"" nm "\""))
                  (setq kg-t0 (KG-SubT0))
                  (setq kg-del (KG-Safe '(lambda () (KG_EXDeleteDef nm)) nil))
                  (KG-SubT1 "очистка: удаление определения (работа)" kg-t0)
                  (if kg-del
                    (progn
                      (setq deleted (cons nm deleted))
                      (setq progress t)
                    )
                  )
                )
              )
              (if deleted
                (princ (strcat "\nСнято определений: "
                               (itoa (length deleted))))
              )
            )
          )

          ;; 71.8 / 72.4. Перед PURGE -- перепривязка паспортов динамики.
          ;; Кандидаты держатся не именами, а сетью динамики: rep-data
          ;; (340 на запись определения) в словарях вставок да xdata
          ;; тега на записях *U. PURGE таких ссылок не видит и
          ;; определения не удаляет. Сборки до 72.4 снимали деревья и
          ;; рвали паспорта живых вставок; теперь ссылки переводятся на
          ;; записи действующих одноимённых определений, паспорта целы.
          ;; Кандидаты пересчитываются перед перепривязкой:
          ;; после возврата ссылок список мог сузиться.
          (if (and KG-CLEANUP-STRIP cand)
            (progn
              (setq holders
                (KG-Unmark (KG-Safe '(lambda () (KG-EXRefHolders)) nil)))
              (setq counts (KG-CleanupCounts holders))
              (setq names (KG-Safe '(lambda () (KG_EXAllDefNames)) nil))
              (setq keep (KG-CleanupKeepAll names))
              (setq cand (KG-CleanupCandidates counts names keep))
              (if cand
                (progn
                  (KG-MarkT "очистка: перепривязка паспортов динамики")
                  (setq kg-t0 (KG-SubT0))
                  (setq kg-del (KG-Safe '(lambda () (KG-CleanupRepRepoint cand)) nil))
                  (KG-SubT1 "очистка: перепривязка паспортов (работа)" kg-t0)
                  (if kg-del
                    (progn
                      (if (> (KG-AsNum (car kg-del) 0) 0)
                        (princ (strcat "\nпаспорта динамики: перепривязано ссылок "
                                       (itoa (KG-AsNum (car kg-del) 0))
                                       ", вставок "
                                       (itoa (KG-AsNum (car (cdr kg-del)) 0))))
                      )
                      (if (> (KG-AsNum (car (cdr (cdr kg-del))) 0) 0)
                        (princ (strcat "\nпаспорта динамики без замены оставлены у вставок: "
                                       (itoa (KG-AsNum (car (cdr (cdr kg-del))) 0))))
                      )
                    )
                  )
                )
              )
            )
          )

          ;; 71.5. Порядок изменён: СНАЧАЛА AutoCAD своим PURGE, и только
          ;; по остатку -- ENTD. Прежний порядок (ENTD первым) стоил
          ;; 19.4 с живого прогона 71.4: 56 попыток стирания больших
          ;; представлений, каждая с полным обходом содержимого
          ;; (проверка MINSERT), при нуле удалённых. PURGE снял 62
          ;; определения за 0.33 с, после него попытки стирания
          ;; занимали доли секунды. Механика та же: PURGE снимает
          ;; освобождённые представления пачкой, ENTD добирает те, что
          ;; PURGE не трогает (их держат словари).
          (KG-MarkT "очистка: PURGE блоков")
          (setq kg-t0 (KG-SubT0))
          (KG-Safe '(lambda () (KG-CleanupPurgeBlocks)) nil)
          (KG-SubT1 "очистка: PURGE блоков (работа)" kg-t0)

          ;; Сиротские *U. PURGE пачку снимает, но запасённые словарями
          ;; не трогает -- по ним ENTD по записи таблицы блоков. Списки
          ;; перечитываются ПОСЛЕ PURGE: часть имён уже снята, и попытки
          ;; по ним были бы пустыми.
          (setq holders
            (KG-Unmark (KG-Safe '(lambda () (KG-EXRefHolders)) nil)))
          (setq counts (KG-CleanupCounts holders))
          (setq names (KG-Safe '(lambda () (KG_EXAllDefNames)) nil))
          (setq keep (KG-CleanupKeepAll names))
          (setq orph (KG-CleanupOrphans counts names))
          (setq noxref (not (KG-Safe '(lambda () (KG_HasXrefDefs)) nil)))
          (if (KG-CleanupEraseAllowed KG-CLEANUP-ERASE-U orph noxref)
            (progn
              (setq round2 0 uor orph goon t)
              (while (and goon uor (< round2 8))
                (setq round2 (1+ round2))
                (setq goon nil)
                (KG-MarkT (strcat "очистка: стирание сиротских *U, проход "
                                 (itoa round2)))
                (setq kg-t0 (KG-SubT0))
                (foreach nm uor
                  (KG-TraceDetail (strcat "стирание \"" nm "\""))
                  (if (KG-Call 'KG_EXEraseAnonDef (list nm) nil)
                    (progn
                      (setq udel (cons nm udel))
                      (setq goon t)
                    )
                    (setq ufail (cons nm ufail))
                  )
                  (setq uwhy
                    (KG-SetAssoc (KG-AsString KG-ERASE-WHY)
                      (1+ (KG-WhyCount KG-ERASE-WHY uwhy))
                      uwhy)
                  )
                  ;; Текст отказа запоминается один раз -- первый непустой:
                  ;; он и печатается в разборе.
                  (if (and (null uerr) (/= (KG-AsString KG-ERASE-ERR) ""))
                    (setq uerr (KG-AsString KG-ERASE-ERR))
                  )
                )
                (KG-SubT1 "очистка: стирание *U (работа)" kg-t0)
                (setq holders
                  (KG-Unmark (KG-Safe '(lambda () (KG-EXRefHolders)) nil)))
                (setq counts (KG-CleanupCounts holders))
                (setq names (KG-Safe '(lambda () (KG_EXAllDefNames)) nil))
                (setq uor (KG-CleanupOrphans counts names))
              )
              (if (and KG-TRACE udel)
                (princ (strcat "\nСтёрто сиротских *U: " (itoa (length udel))))
              )
            )
          )

          ;; Повторная попытка по остатку: стирание выше могло освободить
          ;; представления, которые держались за снятые.
          (setq holders
            (KG-Unmark (KG-Safe '(lambda () (KG-EXRefHolders)) nil)))
          (setq counts (KG-CleanupCounts holders))
          (setq names (KG-Safe '(lambda () (KG_EXAllDefNames)) nil))
          (setq uor2 (KG-CleanupOrphans counts names))
          (setq n1 (length udel))
          (if (and KG-CLEANUP-ERASE-U uor2)
            (progn
              (KG-MarkT (strcat "очистка: стирание *U после PURGE ("
                               (itoa (length uor2)) ")"))
              (foreach nm uor2
                (KG-TraceDetail (strcat "стирание \"" nm "\""))
                (if (KG-Call 'KG_EXEraseAnonDef (list nm) nil)
                  (setq udel (cons nm udel))
                  (setq ufail (cons nm ufail))
                )
                (setq uwhy
                  (KG-SetAssoc (KG-AsString KG-ERASE-WHY)
                    (1+ (KG-WhyCount KG-ERASE-WHY uwhy))
                    uwhy)
                )
                (if (and (null uerr) (/= (KG-AsString KG-ERASE-ERR) ""))
                  (setq uerr (KG-AsString KG-ERASE-ERR))
                )
              )
            )
          )
          ;; Стирание могло освободить определения -- снимаем их сразу,
          ;; не дожидаясь следующего запуска очистки.
          (if (> (length udel) n1)
            (progn
              (KG-MarkT "очистка: PURGE после стирания *U")
              (KG-Safe '(lambda () (KG-CleanupPurgeBlocks)) nil)
            )
          )

          ;; Разбор отказов стирания *U: по одному «не удалось: N» не
          ;; видно, что мешает. Печатается одной строкой и только когда
          ;; отказы есть.
          (if (and KG-TRACE ufail)
            (princ (strcat "\nСиротских *U не стёрлось: "
                           (itoa (length (KG-Unique ufail)))
                           " (многострочная вставка: "
                           (itoa (KG-WhyCount "minsert" uwhy))
                           "; ENTD отказал: "
                           (itoa (KG-WhyCount "entdel" uwhy))
                           "; ename не найден: "
                           (itoa (KG-WhyCount "noent" uwhy))
                           "; определение осталось после ENTD: "
                           (itoa (KG-WhyCount "left" uwhy)) ")")))
          ;; Платформенное объяснение отказа: текст ошибки ENTD, если он был.
          ;; Так «ENTD отказал: 38» превращается в называемую причину.
          (if (and KG-TRACE uerr)
            (princ (strcat "\nENTD ответил: «" uerr "»"))
          )
          (KG-MarkT "очистка: контроль после PURGE")
          (setq holders
            (KG-Unmark (KG-Safe '(lambda () (KG-EXRefHolders)) nil)))
          (setq counts (KG-CleanupCounts holders))
          (setq names (KG-Safe '(lambda () (KG_EXAllDefNames)) nil))
          (setq keep (KG-CleanupKeepAll names))
          (setq left (KG-CleanupCandidates counts names keep))
          (setq orph (KG-CleanupOrphans counts names))
          (if (or (> (length left) 0) (> (length orph) 0))
            (princ (strcat "\nОсталось неиспользуемых: " (itoa (length left))
                           ", сиротских *U: " (itoa (length orph))))
            (princ "\nНеиспользуемых определений не осталось.")
          )
          (if (and KG-TRACE left)
            (progn
              (setq n 0)
              (foreach nm left
                (if (< n 10)
                  (progn
                    (princ (strcat "\n  " nm " -- держит: "
                                   (KG-CleanupHolderText holders nm)))
                    (setq n (1+ n))
                  )
                  (if (= n 10)
                    (progn
                      (princ (strcat "\n  ... и ещё "
                                     (itoa (- (length left) 10))))
                      (setq n (1+ n))
                    )
                  )
                )
              )
            )
          )
          ;; Кто держит остаток НА САМОМ ДЕЛЕ. «Прямых вставок нет» -- это
          ;; про вставки; ссылка может лежать в словаре самого определения:
          ;; PURGE её видит, обход вставок -- нет, отсюда и отказ ENTD.
          ;; Пробы читают словари записей и называют то, на что указывают
          ;; ссылки. Восемь строк: остальное -- числами.
          (if (and KG-TRACE (or left orph))
            (progn
              (KG-MarkT "очистка: разбор словарей остатка")
              (setq n 0)
              (foreach nm (append left orph)
                (if (< n 8)
                  (progn
                    (setq hh (KG-DefDictProbe nm))
                    (princ (strcat "\n  " nm ": "
                                   (if (= hh "") "(словаря не видно)" hh)))
                    (setq n (1+ n))
                  )
                )
              )
              (if (> (length (append left orph)) 8)
                (princ (strcat "\n  ... и ещё "
                               (itoa (- (length (append left orph)) 8))))
              )
            )
          )
        )
        (princ "\nОтменено, чертёж не изменён.")
      )
    )
  )
  (KG-PurgeAnchorsDrop)
  ;; 71.9: возвращается и остаток сиротских *U: без него «ИТОГ ОЧИСТКИ»
  ;; печатал «чисто», пока в чертеже висели десятки *U.
  (list (length left) (length orph))
    )
  )
)

;;;--- RDBCLEANUP (INTCLEANUP, ПДБОЧИСТКА) ---------------------------------
(defun C:RDBCLEANUP ( / r)
  (vl-load-com)
  ;; 71.9: сначала -- возврат по журналу прошлого падения (если он есть):
  ;; переменные, имя мастера и временные вложения защиты от PURGE.
  (KG-Safe '(lambda () (KG-CrashRecover)) nil)
  ;; 71.3: якоря защиты от прошлого прогона, если он падал посреди PURGE
  (KG-Safe '(lambda () (KG-PurgeAnchorsDrop)) nil)
  (KG-TimeReset)
  (setq r (KG-CleanupRun))
  ;; 71.9: очистка завершилась -- журнал этой команды больше не нужен.
  (KG-JournalErase)
  (KG-TimeReport)
  (princ)
)
(defun C:INTCLEANUP () (C:RDBCLEANUP))
(defun C:ПДБОЧИСТКА () (C:RDBCLEANUP))

;;;--- RDBRECOVER (INTRECOVER, ПДБВОССТАНОВЛЕНИЕ): возврат после падения ------
;;; Доводит до конца то, что не успел обработчик ошибок: системные
;;; переменные, имя мастер-версии и временные вложения защиты от PURGE.
;;; Обычно это делает сама следующая команда (RDB, RDBPICK, RDBCHECK,
;;; RDBCLEANUP) -- команда нужна, когда чертёж уже открыт заново.
(defun C:RDBRECOVER ( / )
  (vl-load-com)
  (KG-CrashRecover)
  (princ "\nRDBRECOVER: восстановление завершено.")
  (princ)
)
(defun C:INTRECOVER () (C:RDBRECOVER))
(defun C:ПДБВОССТАНОВЛЕНИЕ () (C:RDBRECOVER))

;;;--- RDBHEAL (INTHEAL, ПДБЛЕЧЕНИЕ) -----------------------------------------
;;; 72.4. Лечение паспортов представлений: для чертежей, испорченных
;;; сборками до 72.4, восстанавливает имя вложенного динамического блока
;;; (в Свойствах показывалось «*U462» вместо «Стойка КП50»). Здоровые
;;; паспорта не трогаются; разбор и механика -- в разделе 72.4 выше.
(defun C:RDBHEAL ( / r)
  (vl-load-com)
  (KG-TimeReset)
  (KG-Say (strcat "=== RDBHEAL: лечение паспортов представлений (сборка "
                  KG-VERSION ") ==="))
  (KG-TimeMark "лечение паспортов: подготовка")
  (setq r (KG-Safe '(lambda () (KG-RepHealRun)) nil))
  (if (null r)
    (KG-Say (strcat "Лечение не выполнено"
                    (if (and KG-FAIL-MSG (/= KG-FAIL-MSG ""))
                      (strcat ": " KG-FAIL-MSG)
                      " (см. отчёт об ошибке)")))
  )
  (KG-TimeReport)
  (princ)
)
(defun C:INTHEAL () (C:RDBHEAL))
(defun C:ПДБЛЕЧЕНИЕ () (C:RDBHEAL))

;;;--- RDBCOUNT (INTCOUNT, ПДБСЧЁТ) -----------------------------------------
;;; Контрольный снимок таблицы блоков: сколько у каждого определения
;;; прямых вставок. Нужен, чтобы проверить очистку ДО и ПОСЛЕ на большом
;;; чертеже: «своих без ссылок» и «сиротских *U» в отчёте -- это числа, а
;;; здесь видно, какие именно определения остались и держит ли их кто-то.
;;; Вывод разбит на три группы, чтобы не понадобилась сортировка строк.
(defun C:RDBCOUNT ( / holders names out n tot grp g nm c)
  (vl-load-com)
  (setq holders (KG-Unmark (KG-Safe '(lambda () (KG-EXRefHolders)) nil)))
  (setq names (KG-Safe '(lambda () (KG_EXAllDefNames)) nil))
  (princ (strcat "\n=== RDBCOUNT: определений "
                 (itoa (length (if names names nil))) " ==="))
  (setq tot 0)
  (foreach grp (list (list "ОПРЕДЕЛЕНИЯ ПРОШЛОЙ ИНТЕГРАЦИИ (~ИМЯ)"
                           '(lambda (x) (KG-IsTempDefName x)))
                     (list "АНОНИМНЫЕ ПРЕДСТАВЛЕНИЯ (*U)"
                           '(lambda (x) (KG-IsAnonDynName x)))
                     (list "ОСТАЛЬНЫЕ"
                           '(lambda (x)
                              (and (not (KG-IsTempDefName x))
                                   (not (KG-IsAnonDynName x))))))
    (setq out nil)
    (foreach nm names
      (if (vl-catch-all-apply (nth 1 grp) (list nm))
        (progn
          (setq c (length (KG-CdrCI nm holders)))
          (setq tot (+ tot c))
          (setq out (cons (strcat "\n  " nm " -- вставок: " (itoa c)) out))
        )
      )
    )
    (princ (strcat "\n" (nth 0 grp) ": " (itoa (length out))))
    (foreach g (reverse out) (princ g))
  )
  (princ (strcat "\nВсего прямых вставок своих определений: " (itoa tot)))
  (princ)
)
(defun C:INTCOUNT () (C:RDBCOUNT))
(defun C:ПДБСЧЁТ () (C:RDBCOUNT))

;;;--- RDBBRIEF (INTBRIEF, ПДБКРАТКО) ---------------------------------------
;;; Короткая выжимка состояния чертежа: десятки строк вместо полного
;;; лога. Нужна потому, что полный лог с KG-TRACE на чертеже с десятками
;;; определений -- это сотни килобайт текста, и в окно чата он не
;;; вставляется. Печатается ровно то, по чему видно, состоялась очистка:
;;; сколько определений осталось, сколько из них без вставок, сколько
;;; сиротских *U и что именно мешает их стереть.
(defun C:RDBBRIEF ( / holders names keep cand orph nodo nu inside dang
                      blocked nm n lines)
  (vl-load-com)
  (setq holders (KG-Unmark (KG-Safe '(lambda () (KG-EXRefHolders)) nil)))
  (setq names (KG-Safe '(lambda () (KG_EXAllDefNames)) nil))
  (if (null names) (setq names nil))
  (setq keep (KG-CleanupKeepAll names))
  (setq cand (KG-CleanupCandidates
               (KG-CleanupCounts holders) names keep))
  (setq orph (KG-CleanupOrphans (KG-CleanupCounts holders) names))
  (setq nodo 0 nu 0)
  (foreach nm names
    (if (KG-IsTempDefName nm) (setq nodo (1+ nodo)))
    (if (KG-IsAnonDynName nm) (setq nu (1+ nu)))
  )
  (princ (strcat "\n=== КРАТКО (сборка " KG-VERSION ") ==="))
  (princ (strcat "\nОпределений всего: " (itoa (length names))))
  (princ (strcat "\n  служебных (~ИМЯ): " (itoa nodo)))
  ;; Кто держит служебные определения. Без этих имён «PURGE не берёт 31
  ;; определение» -- это просто число, а не диагноз.
  (setq lines (KG-Safe '(lambda () (KG-DoHolderLines holders names)) nil))
  (foreach l lines (princ (strcat "\n" l)))
  (princ (strcat "\n  анонимных (*U): " (itoa nu)))
  (princ (strcat "\nСвоих без вставок (кандидаты): " (itoa (length cand))))
  (princ (strcat "\nСиротских *U: " (itoa (length orph))))
  ;; Что держат сироты и что мешает их стереть: две эти строки и есть
  ;; диагноз, когда «Стёрто 0».
  (setq inside (KG-Safe '(lambda () (KG-OrphanContents orph)) nil))
  (if inside
    (princ (strcat "\n  держат вложенные определения: "
                   (itoa (length (KG-Unique
                                   (apply 'append
                                          (mapcar 'cdr inside))))))))
  (setq blocked nil)
  (foreach nm orph
    (if (KG-Safe '(lambda () (KG_HasMInsert nm)) nil)
      (setq blocked (cons nm blocked))
    )
  )
  (princ (strcat "\n  с многострочной вставкой внутри (не стираются): "
                 (itoa (length blocked))))
  (if blocked
    (progn
      (princ "\n  первые из них:")
      (setq n 0)
      (foreach nm (reverse blocked)
        (if (< n 10) (progn (princ (strcat "\n    " nm)) (setq n (1+ n))))
      )
    )
  )
  ;; Вставки, у которых определение пропало. В норме ноль; если не ноль --
  ;; в чертёже есть экземпляры, которые ни на что не указывают, и это надо
  ;; видеть сразу, а не выяснять по косвенным признакам.
  (setq dang (KG-Safe '(lambda () (KG-DanglingInserts)) (list 0 nil)))
  (princ (strcat "\nВставок с отсутствующим определением: "
                 (itoa (KG-AsNum (car dang) 0))))
  (if (> (KG-AsNum (car dang) 0) 0)
    (progn
      (princ "\n  первые из них:")
      (foreach d (car (cdr dang))
        (princ (strcat "\n    " (KG-AsString d))))
    )
  )
  (princ (strcat "\nСтирание *U разрешено: "
                 ;; запасное значение nil, как в KG-CleanupRun: при
                 ;; нечитаемой таблице блоков стирание разрешается
                 (if (KG-CleanupEraseAllowed KG-CLEANUP-ERASE-U orph
                                             (not (KG-Safe
                                                    '(lambda ()
                                                       (KG_HasXrefDefs))
                                                    nil)))
                   "да" "нет")))
  (princ (strcat "\nKG-TRACE = " (if KG-TRACE "t" "nil")))
  (princ)
)
(defun C:INTBRIEF () (C:RDBBRIEF))
(defun C:ПДБКРАТКО () (C:RDBBRIEF))

;; 72.7. Полный отчёт последнего прогона без служебного шума. Нужен,
;; когда журнал AutoCAD обрезан сотнями строк «Удаление блок ...» от PURGE.
(defun KG-PrintReportBuffer (title / )
  (if KG-REPORT-ALL
    (progn
      (princ (strcat "\n" title " ("
                     (itoa (length KG-REPORT-ALL)) " сем.) ==="))
      (foreach pair KG-REPORT-ALL
        (princ (strcat "\n--- Семейство: " (KG-AsString (car pair)) " ---"))
        (foreach s (cdr pair) (princ (strcat "\n" s)))
      )
    )
  )
  (princ)
)
(defun C:RDBREPORT ( / )
  (if (null KG-REPORT-ALL)
    (princ (strcat "\nОтчёт пока не сохранён: выполните RDB или RDBPICK, "
                   "затем повторите RDBREPORT."))
    (KG-PrintReportBuffer "=== ОТЧЁТ ПОСЛЕДНЕГО ПРОГОНА")
  )
)

;; 72.7. Копия отчёта в текстовый файл: даже повтор в хвосте F2 может
;; не поместиться, а файл можно открыть и скопировать целиком.
(defun KG-ReportFilePath ( / p)
  (setq p (getvar "DWGPREFIX"))
  (if (or (null p) (= p ""))
    (setq p (getvar "TEMPPREFIX"))
  )
  (if (or (null p) (= p ""))
    (setq p ".")
  )
  (if (/= (substr p (strlen p) 1) (chr 92))
    (setq p (strcat p (chr 92)))
  )
  (strcat p "RDBREPORT.txt")
)

(defun KG-WriteReportFile ( / fn f pair s)
  (if KG-REPORT-ALL
    (progn
      (setq fn (KG-ReportFilePath))
      (setq f (open fn "w"))
      (if f
        (progn
          (write-line (strcat "RepDblock, сборка " KG-VERSION
                              ", отчёт последнего прогона, семей: "
                              (itoa (length KG-REPORT-ALL))) f)
          (foreach pair KG-REPORT-ALL
            (write-line (strcat "--- Семейство: "
                                (KG-AsString (car pair)) " ---") f)
            (foreach s (cdr pair) (write-line s f))
          )
          (close f)
          (princ (strcat "\nОтчёт сохранён в файл: " fn))
          fn
        )
        (progn
          (princ (strcat "\nНе удалось записать отчёт в файл: " fn))
          nil
        )
      )
    )
  )
)
(defun C:INTREPORT () (C:RDBREPORT))
(defun C:ПДБОТЧЁТ () (C:RDBREPORT))

;;;--- RDBERR (INTERR, ПДБОШИБКА) -------------------------------------------
;;; Короткий отчёт об ошибке: 5-8 строк, которые помещаются в сообщение
;;; даже когда полный лог не отправить. Печатает последнюю ошибку, шаг,
;;; на котором команда упала, и состояние чертежа после падения.
;;; Нужен потому, что KG-ErrorRestore обнуляет KG-LAST-STEP, и к моменту,
;;; когда пользователь садится писать письмо, улики уже нет.
(defun C:RDBERR ( / )
  (princ (strcat "\n=== ОТЧЁТ ОБ ОШИБКЕ (сборка " KG-VERSION ") ==="))
  (princ (strcat "\nОшибка: "
                 (if KG-LAST-ERROR KG-LAST-ERROR
                     "(не записана -- команда не падала)")))
  (princ (strcat "\nПоследний шаг: "
                 (if (and KG-LAST-ERROR-STEP (/= KG-LAST-ERROR-STEP ""))
                   KG-LAST-ERROR-STEP
                   "(не записан)")))
  (princ (strcat "\nKG-TRACE = " (if KG-TRACE "t" "nil")))
  (princ (strcat "\nKG-AUTOCLEAN = " (if KG-AUTOCLEAN "t" "nil")))
  (princ (strcat "\nKG-CLEANUP-ERASE-U = "
                 (if KG-CLEANUP-ERASE-U "t" "nil")))
  (princ (strcat "\nKG-NESTED-COM = "
                 (if KG-NESTED-COM "t" "nil")
                 " (nil -- не читать состояния вложенных блоков)"))
  (if KG-MASTER-FREED
    (princ (strcat "\nОсталось временно переименованное определение: \""
                   (KG-AsString (car KG-MASTER-FREED)) "\" -> \""
                   (KG-AsString (cdr KG-MASTER-FREED)) "\""))
  )
  (princ "\nСостояние чертежа после падения:")
  (KG-Safe '(lambda () (C:RDBBRIEF)) nil)
  (princ)
)
(defun C:INTERR () (C:RDBERR))
(defun C:ПДБОШИБКА () (C:RDBERR))

;;;--- Команды ---------------------------------------------------------------

;; Обработчик ошибок: восстанавливает системные переменные
(defun KG-ErrorRestore (msg / )
  ;; 71.3: если команда падает между PURGE и завершением очистки, якорные
  ;; вложения защиты снимаются здесь -- иначе в чертеже остались бы лишние
  ;; вставки.
  (KG-Safe '(lambda () (KG-PurgeAnchorsDrop)) nil)
  (if KG-SAVED-VARS
    (foreach v KG-SAVED-VARS
      (setvar (car v) (cdr v))
    )
  )
  (if (and msg (/= msg "Function cancelled") (/= msg "quit / exit abort"))
    (progn
      (princ (strcat "\nОШИБКА: " (KG-AsString msg)))
      ;; без AutoCAD место падения не увидеть, поэтому печатаем последний
      ;; начатый шаг -- по нему ошибка находится однозначно
      (if KG-LAST-STEP
        (princ (strcat "\nПоследний шаг: " KG-LAST-STEP))
      )
      ;; И запоминаем: KG-LAST-STEP в конце этой функции обнуляется, и
      ;; без копии место падения исчезало вместе с ним -- следующая
      ;; команда стирала единственную улику, а лог целиком не всегда
      ;; можно прислать.
      (setq KG-LAST-ERROR (KG-AsString msg))
      (setq KG-LAST-ERROR-STEP (KG-AsString KG-LAST-STEP))
      ;; Команда упала между освобождением имени мастер-версии и
      ;; завершением -- возвращаем имя, иначе в списке блоков останется
      ;; определение "~ИМЯ". Возвращаем только если имя свободно:
      ;; если его уже заняло пришедшее из буфера определение, трогать
      ;; его нельзя.
      (if KG-MASTER-FREED
        (progn
          (if (not (KG_EXDefExists (car KG-MASTER-FREED)))
            (progn
              (KG-Safe '(lambda () (KG-RestoreMasterName KG-MASTER-FREED)) nil)
              (princ (strcat "\nОпределение \"" (car KG-MASTER-FREED)
                             "\" возвращено из временного имени \""
                             (cdr KG-MASTER-FREED) "\"."))
            )
            (princ (strcat "\nОпределение осталось под временным именем \""
                           (cdr KG-MASTER-FREED)
                           "\": имя \"" (car KG-MASTER-FREED)
                           "\" занято пришедшим из буфера определением."))
          )
          (setq KG-MASTER-FREED nil)
        )
      )
    )
  )
  ;; 71.9: команда дошла до конца или её поймал *error* -- возврат
  ;; выполнен, журнал незавершённой команды больше не нужен.
  (KG-Safe '(lambda () (KG-JournalErase)) nil)
  (setq KG-LAST-STEP nil)
  (princ)
)

;;;--- Журнал незавершённой команды: файловая часть (сборка 71.9) -------------
;; Чистая часть -- KG-JournalEncode/Split/Parse/Recs -- в разделе 1.

;; Путь журнала: рядом с чертежом, имя включает имя файла чертежа. Пустой
;; DWGPREFIX (чертёж без имени) -- журнал не ведётся: писать некуда.
(defun KG-JournalPath ( / pre nm)
  (setq pre (KG-AsString (KG-Safe '(lambda () (getvar "DWGPREFIX")) "")))
  (setq nm (KG-AsString (KG-Safe '(lambda () (getvar "DWGNAME")) "")))
  (if (or (= pre "") (= nm ""))
    nil
    (strcat pre "RepDblock_journal_" nm ".txt")
  )
)

;; Признак чертежа для журнала: полный путь в верхнем регистре.
(defun KG-JournalDwgId ( / pre nm)
  (setq pre (KG-AsString (KG-Safe '(lambda () (getvar "DWGPREFIX")) "")))
  (setq nm (KG-AsString (KG-Safe '(lambda () (getvar "DWGNAME")) "")))
  (strcase (strcat pre nm))
)

;; Handle вложения-якоря: восстанавливать по handle, а не по ename --
;; handle переживает сохранение файла, ename нет.
(defun KG-JournalAnchorHandle (e / h)
  (setq h (KG-Safe '(lambda () (cdr (assoc 5 (entget e)))) nil))
  (KG-AsString h)
)

;; Строки журнала по текущему состоянию: версия, чертёж, сохранённые
;; переменные, переименованная мастер-версия (если есть), якоря (если есть).
(defun KG-JournalLines ( / out rec)
  (setq out nil)
  (setq out (cons (KG-JournalEncode (list "RepDblockJournal" "1")) out))
  (setq out (cons (KG-JournalEncode (list "VER" KG-VERSION)) out))
  (setq out (cons (KG-JournalEncode (list "DWG" (KG-JournalDwgId))) out))
  (foreach rec KG-SAVED-VARS
    (setq out (cons (KG-JournalEncode
                      (list "VARS" (KG-AsString (car rec))
                            (KG-AsString (cdr rec))))
                    out))
  )
  (if KG-MASTER-FREED
    (setq out (cons (KG-JournalEncode
                      (list "MASTER" (KG-AsString (car KG-MASTER-FREED))
                            (KG-AsString (cdr KG-MASTER-FREED))))
                    out))
  )
  (foreach rec KG-PURGE-ANCHORS
    (setq out (cons (KG-JournalEncode
                      (list "ANCHOR" (KG-AsString (car rec))
                            (KG-JournalAnchorHandle (cdr rec))))
                    out))
  )
  (reverse out)
)

;; Записать журнал по текущему состоянию. Доступность файла -- не гарантия
;; (папка только для чтения), поэтому неудача -- только предупреждение.
(defun KG-JournalWrite ( / path fh line)
  (setq path (KG-JournalPath))
  (if path
    (progn
      (setq fh (KG-Safe '(lambda () (open path "w")) nil))
      (if fh
        (progn
          (foreach line (KG-JournalLines)
            (KG-Safe '(lambda () (write-line line fh)) nil)
          )
          (KG-Safe '(lambda () (close fh)) nil)
          (setq KG-JOURNAL-MINE t)
        )
        (princ (strcat "\nВНИМАНИЕ: журнал восстановления записать "
                       "не удалось (файл недоступен)."))
      )
    )
  )
)

;; Прочитать журнал: записи или nil. Файла нет или он не наш -- nil.
(defun KG-JournalRead (path / fh line lines recs)
  (setq lines nil)
  (setq fh (KG-Safe '(lambda () (open path "r")) nil))
  (if fh
    (progn
      (while (setq line (KG-Safe '(lambda () (read-line fh)) nil))
        (setq lines (cons line lines))
      )
      (KG-Safe '(lambda () (close fh)) nil)
      (setq recs (KG-JournalParse (reverse lines)))
      (if (KG-JournalRecs "RepDblockJournal" recs) recs nil)
    )
    nil
  )
)

;; Удалить СВОЙ журнал (KG-JOURNAL-MINE): чужой -- это улика падения.
(defun KG-JournalErase ( / path)
  (if (and KG-JOURNAL-MINE (setq path (KG-JournalPath)))
    (progn
      (KG-Safe '(lambda () (vl-file-delete path)) nil)
      (setq KG-JOURNAL-MINE nil)
    )
  )
)

;; Найти журнал незавершённой команды и довести возврат до конца.
;; Вызывается в начале команд ДО KG-SaveVars: та перезапишет журнал своим.
(defun KG-CrashRecover ( / path recs id vars master anchors rc nm h e g2 n)
  (setq n 0)
  (setq path (KG-JournalPath))
  (if path
    (progn
      (setq recs (KG-JournalRead path))
      (if recs
        (progn
          (setq id (KG-AsString (nth 1 (car (KG-JournalRecs "DWG" recs)))))
          (princ "\n=== ЖУРНАЛ НЕЗАВЕРШЁННОЙ КОМАНДЫ ===")
          (if (KG-StrEq id (KG-JournalDwgId))
            (progn
              ;; 1. системные переменные
              (setq vars (KG-JournalRecs "VARS" recs))
              (foreach rc vars
                (if (nth 1 rc)
                  (KG-Safe '(lambda () (setvar (nth 1 rc)
                                               (atoi (KG-AsString (nth 2 rc)))))
                           nil)
                )
              )
              (if vars
                (progn
                  (princ "\nСистемные переменные возвращены по журналу:")
                  (foreach rc vars
                    (princ (strcat "\n  " (KG-AsString (nth 1 rc)) " = "
                                   (KG-AsString (nth 2 rc))))
                  )
                )
              )
              ;; 2. имя мастер-версии
              (setq master (car (KG-JournalRecs "MASTER" recs)))
              (if master
                (progn
                  (setq nm (KG-AsString (nth 1 master)))
                  (setq h (KG-AsString (nth 2 master)))
                  (cond
                    ((= h "") nil)
                    ((not (KG_EXDefExists h)) nil)
                    ((KG_EXDefExists nm)
                     (princ (strcat "\nИмя \"" nm "\" уже занято -- "
                                    "определение \"" h "\" оставлено.")))
                    (t
                      (if (KG-Safe '(lambda () (KG-RestoreMasterName
                                                 (cons nm h))) nil)
                        (princ (strcat "\nИмя \"" nm "\" возвращено из "
                                       "временного \"" h "\"."))
                        (princ (strcat "\nВНИМАНИЕ: имя \"" nm "\" вернуть "
                                       "не удалось."))
                      )
                    )
                  )
                )
              )
              ;; 3. якорные вложения -- по handle: ename между сессиями не
              ;; сохраняется. Перед стиранием сверяется группа 2: handle мог
              ;; достаться другому объекту после правок чертежа.
              (setq anchors (KG-JournalRecs "ANCHOR" recs))
              (foreach rc anchors
                (setq h (KG-AsString (nth 2 rc)))
                (if (/= h "")
                  (progn
                    (setq e (KG-Safe '(lambda () (handent h)) nil))
                    (if e
                      (progn
                        (setq g2 (KG-Safe
                                   '(lambda () (cdr (assoc 2 (entget e))))
                                   nil))
                        (if (and g2 (= (type g2) (type ""))
                                 (KG-StrEq (KG-AsString g2)
                                           (KG-AsString (nth 1 rc))))
                          (progn
                            (KG-Safe '(lambda () (entdel e)) nil)
                            (if (KG-IsAnonDynName g2)
                              (KG-Safe '(lambda () (KG_EXEraseAnonDef g2))
                                       nil)
                            )
                            (setq n (1+ n))
                          )
                        )
                      )
                    )
                  )
                )
              )
              (if (> n 0)
                (princ (strcat "\nСнято временных вложений защиты: "
                               (itoa n)))
              )
              (KG-Safe '(lambda () (vl-file-delete path)) nil)
              (setq KG-JOURNAL-MINE nil)
              (princ "\nВосстановление выполнено. Журнал удалён.")
            )
            (progn
              (princ (strcat "\nЖурнал принадлежит другому чертежу (\"" id
                             "\") -- печатаю и удаляю, восстановить его "
                             "здесь нельзя:"))
              (foreach rc recs
                (princ (strcat "\n  " (KG-JournalEncode rc)))
              )
              (KG-Safe '(lambda () (vl-file-delete path)) nil)
            )
          )
        )
      )
    )
  )
  (setq KG-JOURNAL-MINE nil)
  (princ)
)

(defun KG-SaveVars ( / )
  (setq KG-SAVED-VARS
    (list (cons "CMDECHO" (getvar "CMDECHO"))
          (cons "FILEDIA" (getvar "FILEDIA"))
          (cons "CMDDIA"  (getvar "CMDDIA"))
          (cons "NOMUTT"  (getvar "NOMUTT")))
  )
  (setvar "CMDECHO" 0)
  (setvar "FILEDIA" 0)
  (setvar "CMDDIA" 0)
  ;; 71.9: кэш состояний вложенных блоков не переживает начало прогона.
  (setq KG-SCAN-CACHE nil)
  ;; 71.9: журнал незавершённой команды. Если команда упадёт жёстко (не
  ;; через *error*), следующая команда вернёт переменные по этому журналу.
  (KG-JournalWrite)
)

;;;--- RDBCHECK (INTEGRATECHECK, REPDBLOCKCHECK, ПДБЧЕК): скан без изменений (Этап 2) -

(defun C:RDBCHECK ( / *error* model base scan)
  (defun *error* (m) (KG-ErrorRestore m))
  (vl-load-com)
  ;; 71.9: сначала -- возврат по журналу прошлого падения, потом свой журнал
  (KG-Safe '(lambda () (KG-CrashRecover)) nil)
  (KG-SaveVars)
  (setq KG-MODEL-FAMILY nil KG-MODEL-SKIP-PROPS nil)
  (setq model (KG-Safe '(lambda () (KG_DBGetModel)) nil))
  (setq base (getstring t "\nСемейство (например ABC1.01): "))
  (if (= base "")
    (princ "\nОШИБКА: не задано семейство.")
    (progn
      (setq scan (KG-ScanFamily model base 99999999))
      (KG-SayKV "Семейство" base)
      (KG-SayKV "Найдено итераций" (KG-NumStr (length (cdr (assoc "iterations" scan)))))
      (KG-PrintScanReport scan)
      (KG-PrintSpaceReport scan)
    )
  )
  (KG-ErrorRestore nil)
  (princ)
)
(defun C:INTEGRATECHECK () (C:RDBCHECK))
(defun C:REPDBLOCKCHECK () (C:RDBCHECK))
(defun C:ПДБЧЕК () (C:RDBCHECK))

;;;--- RDB (RepDblock, ПОДМЕНАБЛОКА, ПДБ, INTEGRATE): полная подмена/интеграция -----

(defun C:RDB ( / *error* m mastername p base newiter techhandle
                 rep snap snap0 beforedefs afterdefs fb
                 mdl pre preren hsnap nm cln fams fami famn kg-t0)
  (defun *error* (m) (KG-ErrorRestore m) (KG-TimeReport))
  (vl-load-com)
  ;; 71.9: сначала -- возврат по журналу прошлого падения, потом свой журнал
  (KG-Safe '(lambda () (KG-CrashRecover)) nil)
  (KG-SaveVars)
  (KG-TimeReset)
  (setq KG-REPORT-ALL nil KG-REPORT-LAST nil
        KG-REPORT-BUF nil KG-REPORT-CAPTURE nil KG-DYN-FAIL nil)
  (setq KG-MODEL-FAMILY nil KG-MODEL-SKIP-PROPS nil)

  (princ (strcat "\n=== Подмена / интеграция новой итерации семейства (сборка "
                 KG-VERSION ") ==="))
  (if KG-TRACE
    (princ (strcat "\nВключена подробная печать шагов (KG-TRACE: этапы). "
                   "Ещё подробнее: (setq KG-TRACE-DETAIL t). "
                   "Отключается: (setq KG-TRACE nil).")))
  (if KG-TIMING
    (princ (strcat "\nВключены замеры времени (KG-TIMING): строка на каждый шаг "
                   "и сводка в конце. Отключается: (setq KG-TIMING nil).")))
  (setq techhandle nil)
  (setq KG-DO-PASTE nil)
  (setq KG-PRERENAMES nil)
  (setq KG-PREDEFS nil)
  (setq KG-PLAN nil)
  (setq KG-ARRIVED nil)
  (setq KG-PRE-CANDIDATES 0)
  (setq KG-FREED-N 0)
  (setq KG-PRENAME-FAILED nil)
  (setq KG-VERBOSE nil)
  (setq KG-KEEPNAMES nil)
  ;; якоря защиты от прошлого прогона, если он падал посреди PURGE
  (KG-Safe '(lambda () (KG-PurgeAnchorsDrop)) nil)

  ;; Снимок до запроса: по нему видно, вставил ли пользователь блок сам.
  (setq snap0 (KG-SnapshotDrawing))

  ;; Автоматический режим: блок берётся напрямую из буфера обмена (без лишних вопросов и ожидания Enter).
  (setq m nil)

  ;; Режим A: техническая вставка из буфера обмена.
  (if (null m)
    (progn
      (princ "\nВыполняется техническая вставка из буфера...")
      (KG-MarkT "снимок вхождений до вставки")
      (setq snap (KG-SnapshotDrawing))
      (KG-MarkT "снимок таблицы блоков до вставки")
      (setq beforedefs (KG_EXAllDefNames))
      (setq KG-PREDEFS beforedefs)

      ;; Имена освобождаются ДО вставки: PASTECLIP не переопределяет
      ;; существующее определение -- он печатает "Duplicate definition of
      ;; block ... ignored" и подставляет СТАРОЕ. Пока имя занято, ни
      ;; мастер-версия, ни вложенные определения из буфера не приходят.
      ;;
      ;; Семейство мастер-версии до вставки неизвестно, поэтому
      ;; освобождаются имена всех семейств чертежа, а после вставки те из
      ;; них, что буфер НЕ принёс, возвращаются на место. Чужие семейства
      ;; остаются нетронутыми, а нужное получает новое содержимое.
      ;; Снимок может не прочитаться: лучше INTEGRATE продолжится без
      ;; части данных и назовёт причину, чем оборвётся на середине,
      ;; оставив имена освобождёнными.
      (setq mdl (KG-ReadModelNoProps))
      (if (null mdl)
        (princ (strcat "\nВНИМАНИЕ: снимок чертежа не прочитан ("
                       (KG-FailText)
                       "). Интеграция продолжена без него."))
        (KG-MarkT "снимок чертежа прочитан")
      )
      (if (null mdl) (setq mdl (list (cons "defs" nil) (cons "insts" nil)
                                     (cons "layouts" nil))))
      ;; Освобождаются имена ВСЕХ пользовательских определений чертежа.
      ;; Список кандидатов, собранный по старым версиям семейства, на
      ;; реальном чертеже дал ровно одно имя, и 41 вложенное определение
      ;; так и не освободилось. Состав новой мастер-версии до вставки
      ;; неизвестен, поэтому угадывать его не нужно: освобождается всё,
      ;; а чего буфер не принёс -- KG-Step_RollbackNotArrived вернёт под
      ;; прежним именем. Анонимные (*U..., *Model_Space), системные (_...),
      ;; листовые и внешние определения не трогаются.
      (setq pre nil)
      (foreach nm (KG-UserDefNames mdl)
        (if (and (not (KG-IsSystemBlockName nm)) (not (member nm pre)))
          (setq pre (cons nm pre))
        )
      )
      ;; Состояния видимости вложенных блоков читаются ДО освобождения
      ;; имён: после переименования определение живёт под служебным именем,
      ;; а вернуть состояние нужно определению под прежним.
      (KG-MarkT "снимок состояний вложенных блоков")
      (setq kg-t0 (KG-SubT0))
      (KG-Safe '(lambda () (KG-SaveNestedVis)) nil)
      (KG-SubT1 "подготовка: снимок состояний (работа)" kg-t0)
      (setq KG-PRE-CANDIDATES (length pre))
      (KG-MarkT (strcat "освобождение имён до вставки: кандидатов "
                       (KG-NumStr (length pre))))
      (setq KG-PRENAME-FAILED nil)
      (setq kg-t0 (KG-SubT0))
      (setq preren (KG-Step_PreRename (reverse pre) nil nil mdl))
      (KG-SubT1 "подготовка: освобождение имён (работа)" kg-t0)
      (setq KG-FREED-N (length preren))
      (KG-MarkT (strcat "освобождено имён: " (KG-NumStr KG-FREED-N)
                       (if KG-PRENAME-FAILED
                         (strcat ", не удалось: "
                                 (KG-NumStr (length KG-PRENAME-FAILED)))
                         "")))
      ;; Снимок handle берётся ПОСЛЕ переименования и ДО вставки:
      ;; переименование handle не меняет, а подмена определения пришедшим
      ;; из буфера -- меняет. Только так видно вложенные определения,
      ;; которые пришли под тем же самым именем: по именам они не
      ;; отличаются от старых и оказались бы в списке «не пришло».
      (setq hsnap (KG-Safe '(lambda () (KG_EXDefHandleSnapshot)) nil))

      (if (KG_EXPasteAtOrigin)
        (progn
          (setq afterdefs (KG_EXAllDefNames))
          (setq KG-ARRIVED (KG-Step_DetectArrived beforedefs afterdefs))
          (if hsnap
            (foreach nm (KG-Safe '(lambda () (KG-ArrivedByHandle hsnap)) nil)
              (if (not (KG-StrInterCI (list nm) KG-ARRIVED))
                (setq KG-ARRIVED (cons nm KG-ARRIVED))
              )
            )
          )
          ;; Что буфер не принёс -- то не наше: имя возвращается на место.
          (setq preren (KG-Step_RollbackNotArrived preren KG-ARRIVED))
          (setq KG-PRERENAMES preren)
          (KG-MarkT (strcat "занято пришедшими: " (KG-NumStr (length preren))
                           ", вернулось на место: "
                           (KG-NumStr (- KG-FREED-N (length preren)))))
          (KG-ReportArrived beforedefs afterdefs)
          (KG-MarkT "поиск мастер-версии среди пришедших определений")
          ;; 71.3: за один прогон обрабатываются ВСЕ семьи, пришедшие из
          ;; буфера (стойка, ригель, КП50) -- у каждой свой мастер.
          (setq fams (KG-Safe '(lambda ()
                                 (KG-DetectMasterFamilies
                                   KG-ARRIVED
                                   (KG-ReadModelNoProps)))
                              nil))
          (setq mastername (KG-DetectMasterName KG-ARRIVED))
          (setq KG-MASTER-STATE
            (KG-MasterState mastername beforedefs KG-ARRIVED))
          (if mastername
            (progn
              (KG-MarkT (strcat "мастер-версия: " (KG-AsString mastername)
                                ", поиск технического экземпляра"))
              (setq techhandle
                (KG-PickMasterHandle (KG_EXNewInstancesSince snap)))
              (setq p (KG-ParseBlockName mastername))
              (setq base (nth 0 p))
              (setq newiter (nth 1 p))
            )
            ;; из буфера не пришло ни одного определения. Обычная причина:
            ;; пользователь уже вставил блок вручную ДО запуска команды.
            (progn
              ;; FB принимает три аргумента: снимок вхождений, снимок
              ;; таблицы блоков и модель.
              (setq fb (KG-FallbackMasterFromDrawing
                         snap0 beforedefs (KG-ReadModelNoProps)))
              (if (car fb)
                (progn
                  (setq mastername (nth 1 fb))
                  (setq techhandle (nth 2 fb))
                  (setq base (nth 3 fb))
                  (setq newiter (nth 4 fb))
                )
                (progn
                  (KG-Step_RollbackRename preren)
                  (setq preren nil)
                  (setq KG-PRERENAMES nil)
                  (princ (nth 1 fb))
                )
              )
            )
          )
        )
        (progn
          (KG-Step_RollbackRename preren)
          (setq preren nil)
          (setq KG-PRERENAMES nil)
          (princ "\nОШИБКА: вставка из буфера обмена не выполнена.")
        )
      )
    )
    (progn
      (setq mastername (KG-CdrCI "eff" m))
      (setq techhandle (KG-CdrCI "handle" m))
      (setq p (KG-ParseBlockName mastername))
      (setq base (nth 0 p))
      (setq newiter (nth 1 p))
    )
  )

  (if (and (null base) (null fams))
    (princ "\nОШИБКА: не удалось определить мастер-версию.")
    (progn
      (if fams
        ;; 71.3: все семьи буфера за один прогон -- у каждой свой мастер,
        ;; своя интеграция и свой отчёт.
        (progn
          (setq fami 0)
          (setq famn (length fams))
          (foreach f fams
            (setq fami (1+ fami))
            (setq mastername (nth 0 f))
            (setq base (nth 1 f))
            (setq newiter (nth 2 f))
            (if (> famn 1)
              (KG-Say (strcat "--- Семейство " (itoa fami) " из " (itoa famn)
                              ": " (KG-AsString (KG-MakeName base newiter ""))
                              " ---"))
              (progn
                (KG-SayKV "Мастер-версия" (KG-MakeName base newiter ""))
                (KG-SayKV "Семейство / Блок" base)
                (if (/= (KG-IterToStr newiter) "")
                  (KG-SayKV "Новая итерация" (KG-IterToStr newiter))
                  (KG-SayKV "Режим" "подмена блока без версий")
                )
                (KG-Say "Область обработки: весь файл")
              )
            )
            (setq techhandle (KG-FindNewMasterInstance snap mastername))
            (if techhandle
              (KG-MarkT (strcat "семейство " (itoa fami)
                               ": технический экземпляр "
                               (KG-AsString techhandle)))
              (KG-MarkT (strcat "семейство " (itoa fami)
                               ": технический экземпляр не найден"))
            )
            (setq KG-PRERENAMES preren)
            (setq rep (KG-Integrate_Model base newiter techhandle KG-DO-PASTE))
            (KG-MarkT "печать итогового отчёта")
            (KG-PrintIntegrationReport rep)
            ;; 72.3: промежуточные замеры и уборка мусора после семейства.
            (KG-FamilyReport (strcat ", после семейства "
                                      (itoa fami) " из " (itoa famn)))
          )
        )
        (progn
          (KG-SayKV "Мастер-версия" (KG-MakeName base newiter ""))
          (KG-SayKV "Семейство / Блок" base)
          (if (/= (KG-IterToStr newiter) "")
            (KG-SayKV "Новая итерация" (KG-IterToStr newiter))
            (KG-SayKV "Режим" "подмена блока без версий")
          )
          (KG-Say "Область обработки: весь файл")
          (KG-MarkT "интеграция выполнена, печать отчёта")
          (setq KG-PRERENAMES preren)
          (setq rep (KG-Integrate_Model base newiter techhandle KG-DO-PASTE))
          (KG-MarkT "печать итогового отчёта")
          (KG-PrintIntegrationReport rep)
          ;; 72.3: промежуточные замеры и уборка мусора после семейства.
          (KG-FamilyReport ", после семейства")
        )
      )
      (KG-MarkT "регенерация чертежа")
      (command "_.REGEN")
      ;; Очистка -- часть интеграции, а не отдельная обязанность
      ;; пользователя: после замены экземпляров старые определения и
      ;; их анонимные представления всё равно висят мёртвым грузом.
      (if KG-AUTOCLEAN
        (progn
          (KG-MarkT "очистка определений прошлой интеграции")
          (setq cln (KG-CleanupRun))
          ;; Итог очистки отдельной строкой: «не удалось: 37» в середине
          ;; длинного вывода читалось как провал команды, хотя на
          ;; чертёж это не влияет -- остаются лишь неиспользуемые
          ;; определения, которые не видно и которые не мешают.
          ;; 71.9: KG-CleanupRun теперь возвращает (определения *U-остаток),
          ;; поэтому «чисто» не печатается, пока висят сиротские *U.
          (princ (strcat "\n=== ИТОГ ОЧИСТКИ: "
                         (if (or (> (KG-AsNum (car cln) 0) 0)
                                 (> (KG-AsNum (car (cdr cln)) 0) 0))
                           (strcat "осталось неиспользуемых определений: "
                                   (itoa (KG-AsNum (car cln) 0))
                                   ", сиротских *U: "
                                   (itoa (KG-AsNum (car (cdr cln)) 0))
                                   ". На чертёж не влияют, снимаются "
                                   "повторным RDBCLEANUP или PURGE.")
                           "чисто, лишнего не осталось")
                         " ==="))
        )
        (princ (strcat "\nОчистка отключена (KG-AUTOCLEAN = nil)."
                       " Запустите RDBCLEANUP."))
      )
    )
  )
  (KG-TimeReport)
  ;; 72.7. Отчёт ещё раз в самом конце: после очистки журнал забит
  ;; строками PURGE, а этот повтор остаётся в хвосте и копируется целиком.
  (KG-PrintReportBuffer "=== ОТЧЁТ ПОСЛЕДНЕГО ПРОГОНА (повтор после очистки)")
  (KG-WriteReportFile)
  (KG-ErrorRestore nil)
  (princ)
)
(defun C:REPDBLOCK () (C:RDB))
(defun C:ПОДМЕНАБЛОКА () (C:RDB))
(defun C:ПДБ () (C:RDB))
(defun C:INTEGRATE () (C:RDB))

;;;--- RDBPICK (REPDBLOCKPICK, ПДБВЫБОР): ручной выбор мастер-блока на чертеже ---
(defun C:RDBPICK ( / *error* m mastername p base newiter techhandle
                     rep snap snap0 beforedefs afterdefs fb
                     mdl pre preren hsnap nm cln)
  (defun *error* (m) (KG-ErrorRestore m) (KG-TimeReport))
  (vl-load-com)
  ;; 71.9: сначала -- возврат по журналу прошлого падения, потом свой журнал
  (KG-Safe '(lambda () (KG-CrashRecover)) nil)
  (KG-SaveVars)
  (KG-TimeReset)
  (setq KG-REPORT-ALL nil KG-REPORT-LAST nil
        KG-REPORT-BUF nil KG-REPORT-CAPTURE nil KG-DYN-FAIL nil)
  (setq KG-MODEL-FAMILY nil KG-MODEL-SKIP-PROPS nil)
  (setq KG-VERBOSE nil)
  (setq KG-KEEPNAMES nil)
  ;; якоря защиты от прошлого прогона, если он падал посреди PURGE
  (KG-Safe '(lambda () (KG-PurgeAnchorsDrop)) nil)

  (princ (strcat "\n=== Подмена по выбранному мастер-блоку (сборка "
                 KG-VERSION ") ==="))
  (setq snap0 (KG-SnapshotDrawing))
  (setq m (KG-PickMasterFromUser))
  (if (null m)
    (princ "\nМастер-блок не выбран. Для автоматической вставки из буфера используйте команду RDB.")
    (progn
      (setq mastername (KG-CdrCI "eff" m))
      (setq techhandle (KG-CdrCI "handle" m))
      (setq p (KG-ParseBlockName mastername))
      (setq base (nth 0 p))
      (setq newiter (nth 1 p))
      (if (null base)
        (princ "\nОШИБКА: не удалось определить имя мастер-блока.")
        (progn
          (KG-SayKV "Мастер-версия" (KG-MakeName base newiter ""))
          (KG-SayKV "Семейство / Блок" base)
          (if (/= (KG-IterToStr newiter) "")
            (KG-SayKV "Новая итерация" (KG-IterToStr newiter))
            (KG-SayKV "Режим" "подмена блока без версий")
          )
          (KG-Say "Область обработки: весь файл")
          (setq rep (KG-Integrate_Model base newiter techhandle nil))
          (KG-PrintIntegrationReport rep)
          (command "_.REGEN")
          (if KG-AUTOCLEAN
            (progn
              (setq cln (KG-CleanupRun))
              (princ (strcat "\n=== ИТОГ ОЧИСТКИ: "
                             (if (or (> (KG-AsNum (car cln) 0) 0)
                                     (> (KG-AsNum (car (cdr cln)) 0) 0))
                               (strcat "осталось неиспользуемых определений: "
                                       (itoa (KG-AsNum (car cln) 0))
                                       ", сиротских *U: "
                                       (itoa (KG-AsNum (car (cdr cln)) 0))
                                       ". На чертёж не влияют, снимаются повторным RDBCLEANUP или PURGE.")
                               "чисто, лишнего не осталось")
                             " ==="))
            )
          )
        )
      )
    )
  )
  (KG-TimeReport)
  (KG-PrintReportBuffer "=== ОТЧЁТ ПОСЛЕДНЕГО ПРОГОНА (повтор после очистки)")
  (KG-WriteReportFile)
  (KG-ErrorRestore nil)
  (princ)
)
(defun C:REPDBLOCKPICK () (C:RDBPICK))
(defun C:ПДБВЫБОР () (C:RDBPICK))

;; Выбор мастер-блока пользователем (Режим B).
;; Возврат nil (Enter без выбора) означает "использовать буфер обмена".
;;; Выбор мастер-блока пользователем.
;;; Любая ошибка чтения свойств перехватывается: команда не должна рваться,
;;; у пользователя всегда остаётся путь через Enter (вставка из буфера).
(defun KG-PickMasterFromUser ( / sel e r)
  (setq sel (vl-catch-all-apply '(lambda () (entsel "\nМастер-блок: "))))
  (setq e nil)
  (if (and sel (not (KG-IsErr sel))
           (= (type sel) (type (list nil))))
    (setq e (car sel))
  )
  ;; e должен быть именно именем объекта; всё остальное (nil при пустом
  ;; щелчке, variant при отмене) означает "пользователь ничего не выбрал"
  (if (or (null e) (KG-IsErr e) (/= (type e) 'ENAME))
    nil
    (progn
      (setq r (vl-catch-all-apply '(lambda () (KG-MasterFromEntity e))))
      (if (KG-IsErr r)
        (progn
          (KG-Say "")
          (KG-Say "ВНИМАНИЕ: не удалось прочитать свойства выбранного блока:")
          (KG-Say (strcat "  " (vl-princ-to-string r)))
          (KG-Say "Нажмите Enter, чтобы команда сама вставила блок из буфера.")
          nil
        )
        r
      )
    )
  )
)

;; Разобрать выбранное вхождение и собрать его модель
(defun KG-MasterFromEntity (e / obj eff p)
  (setq obj (vlax-ename->vla-object e))
  (setq eff (KG-EffectiveNameOf obj))
  (setq p (KG-ParseBlockName eff))
  (if (and p (= (nth 2 p) ""))
    (KG-InstanceModel obj e)
    (progn
      (KG-Say (KG-MasterRejectMsg eff))
      (KG-Say "Укажите вхождение мастер-версии заново или нажмите Enter")
      (KG-Say "для технической вставки из буфера обмена.")
      nil
    )
  )
)

;; Диагностический шаг: выполнить операцию и напечатать результат.
;; При ошибке печатает, на каком объекте и каком шаге она случилась.
(defun KG-DiagStep (kg-who kg-what kg-fn / kg-res)
  (setq kg-res (vl-catch-all-apply kg-fn))
  (if (KG-IsErr kg-res)
    (KG-Say (strcat "  ОШИБКА [" kg-what "] " kg-who " : "
                    (vl-princ-to-string kg-res)))
    (KG-Say (strcat "  " kg-who "  " kg-what ": " (KG-AsString kg-res)))
  )
  kg-res
)

;;;--- RDBDIAG (INTDIAG, ПДБДИАГ): диагностика чтения чертежа ------------------
;;; Проходит по всем определениям и вхождениям и печатает, на каком объекте
;;; чтение ломается. Ничего не меняет. Нужна, когда RDB падает с
;;; ошибкой типа: по выводу видно конкретное имя блока.
(defun C:RDBDIAG ( / *error* blk nm r ss i e h ok bad firstbad obj m)
  (defun *error* (m) (KG-ErrorRestore m))
  (vl-load-com)
  (KG-SaveVars)
  (setq KG-VERBOSE t)

  (KG-Say (strcat "=== RDBDIAG, сборка " KG-VERSION " ==="))

  ;; 1. определения
  (KG-Say "Определения:")
  (setq ok 0 bad 0 firstbad nil)
  (vlax-for blk (KG-Blocks)
    (setq nm (vl-catch-all-apply '(lambda () (vla-get-Name blk))))
    (if (KG-IsErr nm)
      (setq bad (1+ bad))
      (progn
        (KG-Mark (strcat "определение \"" (KG-AsString nm) "\""))
        (setq r (vl-catch-all-apply
                  '(lambda ()
                     (list (KG-DefNestedRefs nm) (KG-DefVisStates nm)))))
        (if (KG-IsErr r)
          (progn
            (setq bad (1+ bad))
            (if (not firstbad) (setq firstbad nm))
            (KG-Say (strcat "  ОШИБКА  " (KG-AsString nm) " : "
                            (vl-princ-to-string r)))
          )
          (setq ok (1+ ok))
        )
      )
    )
  )
  (KG-SayKV "  прочитано" (itoa ok))
  (KG-SayKV "  с ошибками" (itoa bad))

  ;; 2. вхождения
  (KG-Say "Вхождения:")
  (setq KG-SPACE-MAP (KG-BuildSpaceMap))
  (KG-SayKV "  объектов в карте пространств" (KG-NumStr (length KG-SPACE-MAP)))
  (setq ok 0 bad 0)
  (setq ss (ssget "_X" '((0 . "INSERT"))))
  (if ss
    (repeat (setq i (sslength ss))
      (setq e (ssname ss (setq i (1- i))))
      (setq h (cdr (assoc 5 (entget e))))
      (KG-Mark (strcat "вхождение " (KG-AsString h)))
      ;; каждый шаг чтения отдельно: по выводу видно, что именно ломается
      (setq obj (vl-catch-all-apply '(lambda () (vlax-ename->vla-object e))))
      (if (KG-IsErr obj)
        (progn
          (setq bad (1+ bad))
          (KG-Say (strcat "  ОШИБКА [vla-object] handle " (KG-AsString h)
                          " : " (vl-princ-to-string obj)))
        )
        (progn
          (KG-DiagStep (strcat "handle " (KG-AsString h)) "эффективное имя"
            '(lambda () (KG-EffectiveNameOf obj)))
          (KG-DiagStep (strcat "handle " (KG-AsString h)) "пространство"
            '(lambda () (KG-SpaceOf e)))
          (KG-DiagStep (strcat "handle " (KG-AsString h)) "полная модель"
            '(lambda () (if (KG-InstanceModel obj e) t nil)))
          (if (KG-IsErr (vl-catch-all-apply '(lambda () (KG-InstanceModel obj e))))
            (setq bad (1+ bad))
            (setq ok (1+ ok))
          )
        )
      )
    )
  )
  (KG-SayKV "  прочитано" (itoa ok))
  (KG-SayKV "  с ошибками" (itoa bad))

  ;; 3. разбор имён семейства
  (KG-Say "Имена, которые разбираются как БАЗА vВЕРСИЯ или БАЗА(N):")
  (vlax-for blk (KG-Blocks)
    (setq nm (vl-catch-all-apply '(lambda () (vla-get-Name blk))))
    (if (not (KG-IsErr nm))
      (progn
        (setq r (KG-ParseBlockName nm))
        (if r
          (KG-Say (strcat "  " (KG-AsString nm) "  ->  база \""
                          (KG-AsString (nth 0 r)) "\" итерация \""
                          (KG-AsString (nth 1 r)) "\" вариант \""
                          (KG-AsString (nth 2 r)) "\""))
        )
      )
    )
  )
  (KG-Say "Готово. Чертеж не изменён.")
  (KG-ErrorRestore nil)
  (princ)
)
(defun C:INTDIAG () (C:RDBDIAG))
(defun C:ПДБДИАГ () (C:RDBDIAG))


;;;--- RDBDUMP (INTDUMP, ПДБДАМП): диагностика экземпляра -------------------
(defun C:RDBDUMP ( / e obj dp vis allowed nm)
  (vl-load-com)
  (setq e (car (entsel "\nВыберите блок для диагностики: ")))
  (if e
    (progn
      (setq obj (vlax-ename->vla-object e))
      (KG-Say "=== RDBDUMP ===")
      (KG-SayKV "Name" (cdr (assoc 2 (entget e))))
      (KG-SayKV "EffectiveName" (KG-EffectiveNameOf obj))
      (KG-SayKV "Handle" (cdr (assoc 5 (entget e))))
      (KG-SayKV "Layout" (KG-SpaceOf e))
      (KG-SayKV "Layer" (vla-get-Layer obj))
      (KG-SayKV "InsertionPoint" (vl-princ-to-string (vla-get-InsertionPoint obj)))
      (KG-SayKV "Scale"
        (strcat (rtos (vla-get-XScaleFactor obj) 2 4) " / "
                (rtos (vla-get-YScaleFactor obj) 2 4) " / "
                (rtos (vla-get-ZScaleFactor obj) 2 4)))
      (KG-SayKV "Rotation" (rtos (vla-get-Rotation obj) 2 6))
      (KG-SayKV "IsDynamicBlock"
        (if (KG-ComBool
              (vl-catch-all-apply '(lambda () (vla-get-IsDynamicBlock obj))))
          "T" "nil"))
      (setq allowed (KG-GetAllowedVisibilityStates obj))
      (KG-SayKV "AllowedValues" (if allowed (vl-princ-to-string allowed) "нет"))
      (KG-SayKV "Visibility" (KG-GetVisibilityState obj))
      (KG-Say "DynamicProperties:")
      (setq dp (KG-GetDynamicProperties obj))
      (if dp
        (foreach p dp
          (princ (strcat "\n  " (KG-AsString (car p)) " = "
                         (vl-princ-to-string (cdr p)))))
        (princ "\n  нет")
      )
      (KG-Say "Nested visibility:")
      (setq nm (KG-InstanceNestedVisibility obj nil))
      (if nm
        (foreach p nm
          (princ (strcat "\n  " (KG-AsString (car p)) " = "
                         (if (cdr p) (KG-AsString (cdr p)) "-"))))
        (princ "\n  нет")
      )
    )
  )
  (princ)
)
(defun C:INTDUMP () (C:RDBDUMP))
(defun C:ПДБДАМП () (C:RDBDUMP))

;;;--- RDBDUMPDEF (INTDUMPDEF, ПДБДАМПОПР): диагностика определения (Этап 0.5)

(defun C:RDBDUMPDEF ( / nm)
  (vl-load-com)
  (setq nm (getstring t "\nИмя определения блока: "))
  (if (/= nm "")
    (progn
      (KG-Say "=== RDBDUMPDEF ===")
      (KG-SayKV "Определение" nm)
      (KG-SayKV "Существует" (if (KG_EXDefExists nm) "да" "нет"))
      (KG-SayKV "Вложенные ссылки" (vl-princ-to-string (KG-DefNestedRefs nm)))
      (KG-SayKV "Рекурсивно вложенные"
                (vl-princ-to-string
                  (KG-GetNestedBlocks (KG_DBGetModel) nm)))
      (KG-SayKV "Состояния видимости" (vl-princ-to-string (KG-DefVisStates nm)))
      (KG-SayKV "Состояния вложенных" (vl-princ-to-string (KG-DefNestedVisibility nm)))
    )
  )
  (princ)
)
(defun C:INTDUMPDEF () (C:RDBDUMPDEF))
(defun C:ПДБДАМПОПР () (C:RDBDUMPDEF))

;;;--- RDBPASTETEST (INTPASTETEST, ПДБТЕСТВСТАВКИ): диагностика вставки из буфера (Этап 0.6) -
;;; Отвечает на ключевой вопрос этапа: что реально приходит из буфера и
;;; переименовываются ли конфликтующие определения.

(defun C:RDBPASTETEST ( / snap before after newdefs gone i nm newinst h)
  (vl-load-com)
  (KG-SaveVars)
  (KG-Say "=== RDBPASTETEST ===")
  (princ "\nСкопируйте мастер-блок в исходном файле, затем нажмите Enter.")
  (getstring "\nEnter для продолжения: ")
  (setq snap (KG-SnapshotDrawing))
  (setq before (KG_EXAllDefNames))
  (if (KG_EXPasteAtOrigin)
    (progn
      (setq after (KG_EXAllDefNames))
      (setq newdefs (KG-StrDiffCI after before))
      (setq gone (KG-StrDiffCI before after))
      (KG-Say "Новые определения после вставки:")
      (if newdefs
        (foreach nm newdefs (KG-Say (strcat "  + " (KG-AsString nm))))
        (KG-Say "  (нет — вероятно, сработало 'Duplicate definition ignored')")
      )
      (KG-Say "Переименованные/исчезнувшие определения:")
      (if gone
        (foreach nm gone (KG-Say (strcat "  - " (KG-AsString nm))))
        (KG-Say "  (нет)")
      )
      ;; Анонимные определения (*U118, *D3 ...) служебными НЕ считаются:
      ;; их создаёт сам AutoCAD, в том числе при вставке динамического
      ;; блока. Иначе список состоял бы только из них.
      (KG-Say "Определения со служебными суффиксами в имени:")
      (setq i nil)
      (foreach nm after
        (if (and (not (KG-IsAnonymousName nm))
                 (KG-IsServiceName nm)
                 (not (member nm before)))
          (progn (KG-Say (strcat "  ! " (KG-AsString nm))) (setq i t))
        )
      )
      (if (not i) (KG-Say "  (нет)"))
      (KG-Say "Новые экземпляры:")
      (setq newinst (KG_EXNewInstancesSince snap))
      (foreach h newinst
        (KG-Say (strcat "  handle " (KG-AsString h) " -> "
                        (KG-CdrCI "eff" (KG_EXInstanceHandle h)))))
      ;; Команда диагностическая, поэтому свою вставку убирает сама.
      ;; Копия мастер-версии, оставленная в начале координат, потом
      ;; попадает в RDB как лишний экземпляр новой итерации и даёт
      ;; ложное расхождение счётчика и ложную «потерю».
      (foreach h newinst (KG_EXDeleteInstance h))
      (if newinst
        (princ (strcat "\nТехническая вставка удалена ("
                       (KG-NumStr (length newinst))
                       " шт.), чертёж в том же составе, что до команды."))
        (princ "\nНовых экземпляров нет.")
      )
    )
    (princ "\nОШИБКА: вставка из буфера не выполнена.")
  )
  (KG-ErrorRestore nil)
  (princ)
)
(defun C:INTPASTETEST () (C:RDBPASTETEST))
(defun C:ПДБТЕСТВСТАВКИ () (C:RDBPASTETEST))

;;;--- RDBTESTBED (INTTESTBED, ПДБСТЕНД): построение тестового стенда (Этап 0)
;;; Создаёт СТАТИЧЕСКИЕ блоки с правильными именами. Динамические параметры
;;; добавляются вручную в редакторе блоков (LISP не может их создавать).

(defun C:RDBTESTBED ( / names nm)
  (setq names '("ABC1.01(1)Стойка" "ABC1.01(2)Ригель"
                "ABC1.01(3)Крышка" "ABC1.01(4)"))
  (foreach nm names
    (if (not (tblsearch "BLOCK" nm))
      (progn
        (entmake (list (cons 0 "BLOCK") (cons 2 nm) (cons 70 2)
                       (cons 10 (list 0.0 0.0 0.0))))
        (entmake (list (cons 0 "CIRCLE") (cons 8 "0")
                       (cons 10 (list 0.0 0.0 0.0)) (cons 40 100.0)))
        (entmake (list (cons 0 "TEXT") (cons 8 "0")
                       (cons 10 (list 120.0 0.0 0.0)) (cons 40 50.0)
                       (cons 1 nm)))
        (entmake (list (cons 0 "ENDBLK") (cons 8 "0")))
      )
    )
  )
  ;; экземпляры: часть в модели
  (entmake (list (cons 0 "INSERT") (cons 2 "ABC1.01(1)Стойка")
                 (cons 10 (list 0.0 0.0 0.0)) (cons 41 1.0)
                 (cons 42 1.0) (cons 43 1.0) (cons 50 0.0)))
  (entmake (list (cons 0 "INSERT") (cons 2 "ABC1.01(2)Ригель")
                 (cons 10 (list 1000.0 0.0 0.0)) (cons 41 1.0)
                 (cons 42 1.0) (cons 43 1.0) (cons 50 0.0)))
  (entmake (list (cons 0 "INSERT") (cons 2 "ABC1.01(3)Крышка")
                 (cons 10 (list 2000.0 0.0 0.0)) (cons 41 1.0)
                 (cons 42 1.0) (cons 43 1.0) (cons 50 0.0)))
  (entmake (list (cons 0 "INSERT") (cons 2 "ABC1.01(4)")
                 (cons 10 (list 3000.0 0.0 0.0)) (cons 41 1.0)
                 (cons 42 1.0) (cons 43 1.0) (cons 50 0.0)))
  (KG-Say "Тестовый стенд создан (статические блоки).")
  (KG-Say "Для полной проверки добавьте вручную:")
  (KG-Say "  1. параметр видимости в каждом блоке (BEDIT -> Visibility);")
  (KG-Say "  2. экземпляры на листы;")
  (KG-Say "  3. мастер-версию ABC1.01(5) с вложенными блоками.")
  (command "_.REGEN")
  (princ)
)
(defun C:INTTESTBED () (C:RDBTESTBED))
(defun C:ПДБСТЕНД () (C:RDBTESTBED))


;; Баннер загрузки: краткое описание и таблица команд.
;; Один princ: check_load ищет все имена команд в одном блоке.
(princ
  (strcat
    "\nRepDblock.lsp, сборка " KG-VERSION " — подмена динамических блоков."
    "\nБерёт из буфера новую итерацию семейства и заменяет ею старые вхождения:"
    "\nсоздаёт варианты, обновляет вложенные определения, возвращает видимость"
    "\nи динамические свойства, затем чистит старые определения."
    "\nКоманды: "
    "\n  +--------------------------------+------------------------------+"
    "\n  | " (KG-Pad "КОМАНДА" 30) " | " (KG-Pad "ЧТО ДЕЛАЕТ" 28) " |"
    "\n  +--------------------------------+------------------------------+"
    "\n  | " (KG-Pad "ПДБ / ПОДМЕНАБЛОКА (RDB)" 30) " | " (KG-Pad "заменить семейство из буфера" 28) " |"
    "\n  | " (KG-Pad "ПДБВЫБОР (RDBPICK)" 30) " | " (KG-Pad "заменить по выбранному блоку" 28) " |"
    "\n  | " (KG-Pad "ПДБОЧИСТКА (RDBCLEANUP)" 30) " | " (KG-Pad "очистка старых определений" 28) " |"
    "\n  | " (KG-Pad "ПДБВОССТАНОВЛЕНИЕ (RDBRECOVER)" 30) " | " (KG-Pad "восстановление после сбоя" 28) " |"
    "\n  | " (KG-Pad "ПДБЛЕЧЕНИЕ (RDBHEAL)" 30) " | " (KG-Pad "лечение паспортов динамики" 28) " |"
    "\n  +--------------------------------+------------------------------+"
    "\n  Подробно: (setq KG-TRACE-DETAIL t)."
    "\n  Порядок прогона: docs/ИНСТРУКЦИЯ_ПРОГОН.md"
  ))
(princ)
